FME workspace backupConfiguration.fmw
Description: Backup FME Flow configuration to an FME Flow Configuration package (.fsconfig) file. By default, the configuration file is saved to the Backup shared resources and the date and time of the backup are appended to the filename. The backup contains the repositories, services, security, notifications, schedules and data shared resources. Ensure you have superuser role to run workspace.
History: 03-23-2023,Kezia Y,Upgraded transformers, added description, removed 'server' from parameters

Parameters:
- BACKUP_APPEND_DATE = Yes   # Append Date
- SERVER_USERNAME = admin   # Flow Username
- SERVER_PASSWORD =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   # Flow Password
- BACKUP_DESTINATION = Folder/FlowConfigPackage.fsconfig   # Backup File Name with File Extension (.fsconfig)
- ResourceName = FME_SHAREDRESOURCE_BACKUP   # Resource Name

Creator
    GEOMTYPE = Geometry Object
    NUM = 1
    CREATED -> Tester
Tester
    BOOL_OP = OR
    TEST_CLAUSE = TEST $(BACKUP_APPEND_DATE) = No
    TEST_MODE = TEST
    PASSED -> HTTPCaller
    FAILED -> ParameterFetcher
HTTPCaller
    AUTH_METHOD = Basic
    AUTH_PASSWORD = $(SERVER_PASSWORD)
    AUTH_USERNAME = $(SERVER_USERNAME)
    CONNECTION_TIMEOUT_LENGTH = 0
    ERROR_ATTR = _error
    FOLLOW_REDIRECTS = DO_NOT_FOLLOW
    HTTP_METHOD = POST
    MAX_HTTP_VERSION = HTTP_2
    MAX_TRANSFERS_IN_PROGRESS = 25
    MINIMUM_ENCRYPTION_LEVEL = OS_DEFAULT
    RESPONSE_HEADER_LIST_ATTR = _headers
    RESPONSE_TYPE = Attribute
    SPLIT_MULTIPART_DOWNLOADS = NO
    STATUS_CODE_ATTR = _http_status_code
    TARGET_ATTR = _response_body
    TARGET_ATTR_ENCODING = auto-detect
    TARGET_URL = $(FME_SERVER_WEB_URL)/fmerest/v3/migration/backup/resource
    TRANSFER_TIMEOUT_LENGTH = 0
    UPLOAD_BODY = exportPackage=$(BACKUP_DESTINATION)&resourceName=$(ResourceName)
    UPLOAD_CONTENT_TYPE = URL Encoded (application/x-www-form-urlencoded)
    UPLOAD_TYPE = Specify Upload Body
    USE_COOKIES = No
    VERIFY_SSL_CERTIFICATES = No
    <REJECTED> -> Terminator
HTTPCaller_2
    AUTH_METHOD = Basic
    AUTH_PASSWORD = $(SERVER_PASSWORD)
    AUTH_USERNAME = $(SERVER_USERNAME)
    CONNECTION_TIMEOUT_LENGTH = 0
    ERROR_ATTR = _error
    FOLLOW_REDIRECTS = DO_NOT_FOLLOW
    HTTP_METHOD = POST
    MAX_HTTP_VERSION = HTTP_2
    MAX_TRANSFERS_IN_PROGRESS = 25
    MINIMUM_ENCRYPTION_LEVEL = OS_DEFAULT
    RESPONSE_HEADER_LIST_ATTR = _headers
    RESPONSE_TYPE = Attribute
    SPLIT_MULTIPART_DOWNLOADS = NO
    STATUS_CODE_ATTR = _http_status_code
    TARGET_ATTR = _response_body
    TARGET_ATTR_ENCODING = auto-detect
    TARGET_URL = $(FME_SERVER_WEB_URL)/fmerest/v3/migration/backup/resource
    TRANSFER_TIMEOUT_LENGTH = 0
    UPLOAD_BODY = exportPackage=@Value(PathWithTimestamp)&resourceName=$(ResourceName)
    UPLOAD_CONTENT_TYPE = URL Encoded (application/x-www-form-urlencoded)
    UPLOAD_TYPE = Specify Upload Body
    USE_COOKIES = No
    VERIFY_SSL_CERTIFICATES = No
    <REJECTED> -> Terminator
Terminator
    MESSAGE = Unable to retrieve backup from FME Flow `$(FME_SERVER_WEB_URL)'. Please ensure that the credentials are correct and that user `$(SERVER_USERNAME)' has fmesuperuser role. The error was: @Value(_error).

Bookmark: Adding Timestamp
ParameterFetcher
    ATTR_LIST = _BACKUP_DESTINATION $(BACKUP_DESTINATION)
    -> FilenamePartExtractor
FilenamePartExtractor
    DIRNAME_ATTR = _dirname
    DIRPATH_ATTR = _dirpath
    EXTENSION_ATTR = _extension
    FULLNAME_ATTR = _filename
    ROOTNAME_ATTR = _rootname
    SRC_ATTR = @Value(_BACKUP_DESTINATION)
    -> DateTimeStamper
DateTimeStamper
    DATETIME_ATTR = _timestamp
    INCLUDE_FRAC_SECONDS = YES
    INCLUDE_OFFSET = NO
    STAMP_TYPE = datetime
    TIMEZONE = utc
    -> DateTimeConverter
DateTimeConverter
    DATETIME_ATTR = _timestamp
    OUT_FORMAT = %Y%m%d%H%M
    PASSTHROUGH = NO
    REPAIR_INPUT = YES
    -> StringConcatenator
StringConcatenator
    ACTION = Create New Attribute
    PARM_LINE = @Value(_dirpath)@Value(_rootname)_@Value(_timestamp).@Value(_extension)
    VAL_ATTR = PathWithTimestamp
    -> HTTPCaller_2
