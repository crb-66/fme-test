FME workspace DATA_VALIDATION.fmw

Parameters:
- SourceDataset_SNOWFLAKE_NONSPATIAL = DEV_snowflake_DEV-CDO-PORTFOLIO-MANAGEMENT-PL-MI-srvacct   # Connection
- SourceDataset_GEODATABASE_SDE = FME-ILS-DEV-RO-V2   # ArcSDE Geodatabase Connection
- FEATURE_TYPES = dbo.Mills

Readers:
- SNOWFLAKE_NONSPATIAL_1: SNOWFLAKE_NONSPATIAL from $(SourceDataset_SNOWFLAKE_NONSPATIAL)
- GEODATABASE_SDE_1: GEODATABASE_SDE from $(SourceDataset_GEODATABASE_SDE)

Bookmark: SOURCES_TO_VALIDATE
PORTFOLIO_PL_MI_FACT_TOTAL_PINE_ROUNDWOOD_DEMAND (reader SNOWFLAKE_NONSPATIAL_1)
    attributes: CK varchar(16777216), CHIP_PRODUCTION_RATE number(3,2), CHIP_PRODUCTION number(38,6), FORISK_MILL_ID varchar(16777216), ILS_MILL_ID varchar(16777216), MILL_CAPACITY_ID varchar(16777216), MILL_STATUS_ID_MI number(18,0), MILL_STATUS_ID_FORISK number(18,0), MILL_TYPE varchar(60), PELLET_ADJUSTMENT number(3,2), PINE_ROUNDWOOD_DEMAND number(38,0), PINE_ROUNDWOOD_DEMAND_ADJUSTMENT number(38,6), SPECIES_MULTIPLIER number(3,2), OPERATING_RATE number(38,2), WOOD_DEMAND_AT_CAPACITY number(38,0), WOOD_DEMAND_AT_CAPACITY_ADJUSTED number(38,0)
    -> Test_Snowflake_Data

Bookmark: VALIDATION_TESTS
Test_Snowflake_Data: Tester
    BOOL_OP = COMPOSITE
    COMPOSITE_TEST = 1 AND 2 AND 3 AND 4 AND 5 AND 6 AND 7 AND 8
    TEST_CLAUSE:
      TEST CK ATTRIBUTE_HAS_A_VALUE ""
      TEST CK NOT_ATTRIBUTE_VALUE_NULL ""
      TEST CK NOT_ATTRIBUTE_IS_EMPTY ""
      TEST CK NOT_ATTRIBUTE_IS_MISSING ""
      TEST PINE_ROUNDWOOD_DEMAND NOT_ATTRIBUTE_IS_MISSING ""
      TEST WOOD_DEMAND_AT_CAPACITY_ADJUSTED NOT_ATTRIBUTE_IS_MISSING ""
      TEST MILL_CAPACITY_ID NOT_ATTRIBUTE_IS_MISSING ""
      TEST ILS_MILL_ID NOT_ATTRIBUTE_IS_MISSING ""
    TEST_MODE = TEST
    FAILED -> NoFeaturesTester
Test_ILS_Data: Tester
    BOOL_OP = COMPOSITE
    COMPOSITE_TEST = 1 AND 2
    TEST_CLAUSE:
      TEST MillID NOT_ATTRIBUTE_IS_MISSING ""
      TEST MillID NOT_ATTRIBUTE_VALUE_NULL ""
    TEST_MODE = TEST
    FAILED -> NoFeaturesTester
NoFeaturesTester
    NoInput -> FMEFlowJobSubmitter
    -> FMEFlowNotifier

Bookmark: ILS mills
Mills (reader GEODATABASE_SDE_1)
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50)
    -> Test_ILS_Data

Bookmark: TODO
Note: need to change to TPRWD
Note: failing with incorrect parameters
FMEFlowJobSubmitter
    ACTION = SUBMIT_JOB
    BLOCKING = TRUE
    REPOSITORY = DEV_USER_MCCUNEE
    SERVER_CONNECTION = mccunee FME Flow
    TM_TAG = Default
    WORKSPACE_NAME = Mill_ILS_ChangeDetection.fmw
    WORKSPACE_PARAMETERS = SourceDataset_GEODATABASE_FILE list \\TLTSTAPGISFME01\FME_Share\LeonardL1\Python\ChangeDetector\MillsForChangeDetection.gdb SourceDataset_GEODATABASE_FILE_4 list \\TLTSTAPGISFME01\FME_Share\LeonardL1\Python\ChangeDetector\MillsForChangeDetection.gdb SourceDataset_GEODATABASE_FILE_7 list $(FME_MF_DIR_ENCODED)Redo\MillsForChangeDetection.gdb

Bookmark: VALIDATION_EVENTS
FMEFlowNotifier
    BODY = FAILURE - Validation failed for TPRWD in FME
    SERVER_CONNECTION = mccunee FME Flow
    TOPIC = VALIDATION_FAILURE
    -> Terminator
Terminator
    MESSAGE = Translation Terminated- TPRWD of input sources FAILED
