FME workspace Mill_ILS_ChangeDetection.fmw

Parameters:
- SourceDataset_GEODATABASE_FILE = \\TLTSTAPGISFME01\FME_Share\LeonardL1\Python\ChangeDetector\MillsForChangeDetection.gdb   # File Geodatabase
- SourceDataset_GEODATABASE_FILE_4 = \\TLTSTAPGISFME01\FME_Share\LeonardL1\Python\ChangeDetector\MillsForChangeDetection.gdb   # File Geodatabase
- SourceDataset_GEODATABASE_FILE_7 = C:\Users\McCuneE\Documents\FME\Workspaces\Redo\MillsForChangeDetection.gdb   # File Geodatabase

Readers:
- GEODATABASE_FILE_1: GEODATABASE_FILE from $(SourceDataset_GEODATABASE_FILE)
- GEODATABASE_FILE_2: GEODATABASE_FILE from $(SourceDataset_GEODATABASE_FILE_4)
- GEODATABASE_FILE_3: GEODATABASE_FILE from $(SourceDataset_GEODATABASE_FILE_7)
- GEODATABASE_SDE_1: GEODATABASE_SDE from $(TLDEVDBSFRS01_FIRST_FIRSTDW_Editor_V2)

Bookmark: MILL CHANGE DETECTION
Creator
    GEOMTYPE = Geometry Object
    NUM = 1
    CREATED -> Step1A:_Delete_Delta_Portal_Items
Note: This will be the version in ILS
Note: Python Script to Delete Mill Deltas in UAT Portal
Note: Python Code Needs work to handle Environments
Step1A:_Delete_Delta_Portal_Items: SystemCaller
    ATTR = python_exitcode
    CMD = E:\Projects\PythonProEnv\python.exe "\\TLTSTAPGISFME01\FME_Share\LeonardL1\Python\ChangeDetector\DeltaDeletePortalLayers.py"
    -> Step1B:Tester
Step1B:Tester: Tester
    BOOL_OP = OR
    TEST_CLAUSE = TEST @Value(python_exitcode) = 0
    TEST_MODE = TEST
    PASSED -> Step2:_Detect_Changes_in_Mills [ORIGINAL]
    FAILED -> Step1C:Portal_Delete_Terminator
Step1C:Portal_Delete_Terminator: Terminator
    MESSAGE = Translation Terminated due to errors with deleting portal items.
Note: Check values, as I've seen open vs Open etc. Mills data needs to be cleaned and Status checked with QA
Note: Todo, make a copy for comparison for Debugging
Note: Keep For debugging
Step1E:AttributeFilter: AttributeFilter
    ATTR_NAME = Status
    ATTR_VALUES = <Empty>,Unknown,Open,Closed,Announced,Under Construction,<Missing>,Idle,NA,open,<Null>,<Unfiltered>
    Unknown -> Step2:_Detect_Changes_in_Mills [REVISED]
    Open -> Step2:_Detect_Changes_in_Mills [REVISED]
    Closed -> Step1F:AttributeManager
    Announced -> Step2:_Detect_Changes_in_Mills [REVISED]
    Under Construction -> Step2:_Detect_Changes_in_Mills [REVISED]
    Idle -> Step2:_Detect_Changes_in_Mills [REVISED]
    NA -> Step2:_Detect_Changes_in_Mills [REVISED]
    open -> Step2:_Detect_Changes_in_Mills [REVISED]
Step1F:AttributeManager: AttributeManager
    ATTR_TABLE:
      REMOVE OBJECTID (int32)
      REMOVE Source (varchar(255))
      SET_TO MillID (char(8)) = @Value(MillID)
      REMOVE MillName (varchar(255))
      REMOVE ParentCompany (varchar(255))
      REMOVE City (varchar(255))
      REMOVE State (varchar(255))
      REMOVE PrimaryMillType (varchar(255))
      REMOVE SubMillType (varchar(255))
      REMOVE Status (varchar(255))
      REMOVE TL_Region (varchar(100))
      REMOVE TL_Area (varchar(100))
      REMOVE MicroMarketName (varchar(50))
      REMOVE MicroMarketID (int16)
      REMOVE Latitude (real64)
      REMOVE Longitude (real64)
      REMOVE ModifiedOn (datetime)
      REMOVE Address1 (varchar(255))
      REMOVE Address2 (varchar(255))
      REMOVE Address3 (varchar(255))
      REMOVE Country (varchar(50))
      REMOVE ZipCode (varchar(10))
      REMOVE DestinationID (varchar(50))
      REMOVE LIMSName (varchar(100))
      REMOVE MapLabel (varchar(255))
      REMOVE ForiskID (varchar(50))
      REMOVE ForiskName (varchar(200))
      REMOVE ForiskStatus (varchar(50))
      REMOVE Region (varchar(50))
      REMOVE Capacity (real64)
      REMOVE Units (varchar(50))
      REMOVE Species (varchar(50))
      REMOVE EndUse (varchar(200))
      REMOVE Demand_tons (int32)
      REMOVE RecycledPct (real64)
      REMOVE Newsprint (real64)
      REMOVE Printing_Writing (real64)
      REMOVE Household_Sanitary (real64)
      REMOVE Packaging (real64)
      REMOVE Specialty_DissolvingPulp (real64)
      REMOVE MarketPulp (real64)
      REMOVE Certification (varchar(50))
    USER_EXPOSED_ATTRIBUTES = name,OBJECTID,Source,MillID,MillName,ParentCompany,City,State,PrimaryMillType,SubMillType,Status,TL_Region,TL_Area,MicroMarketName,MicroMarketID,Latitude,Longitude,ModifiedOn,Address1,Address2,Address3,Country,ZipCode,DestinationID,LIMSName,MapLabel,ForiskID,ForiskName,ForiskStatus,Region,Capacity,Units,Species,EndUse,Demand_tons,RecycledPct,Newsprint,Printing_Writing,Household_Sanitary,Packaging,Specialty_DissolvingPulp,MarketPulp,Certification
    -> Step1G:CreateClosedList [Inserted]
Step1G:CreateClosedList: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step1H:RemoveExistingClosedMillsMillsRing [INITIATOR]
    SUMMARY -> Step1I:RemoveExistingClosedMillsMillsDrive [INITIATOR]
    SUMMARY -> Step1J:RemoveExistingClosedMillsFromODMatrix [INITIATOR]
    SUMMARY -> Step1K:RemoveExistingClosedMillsFromODPaths [INITIATOR]
Step2:_Detect_Changes_in_Mills: ChangeDetector
    BLANK_AND_MISSING_DIFFER = Yes
    CHECK_COORDINATE_SYSTEMS = No
    CHECK_TYPES_AND_ENCODINGS = Yes
    LENIENT_MATCH = No
    MATCH = 2D
    MATCHATTRS = MillID Latitude Longitude
    MATCH_STRATEGY = Match Selected Attributes
    PREEMPTIVE_ATTRS = MillID
    UNCHANGED_OUTPUT = Output Revised
    UPSERT_MODE = No
    INSERTED -> Step2B:AttributeManager
    INSERTED -> Step2A:AttributeManager
Step2B:AttributeManager: AttributeManager
    ATTR_TABLE:
      REMOVE OBJECTID (int32)
      REMOVE Source (varchar(255))
      RENAME_SET_VALUE MillID (char(8)) = @Value(MillID)
      REMOVE MillName (varchar(255))
      REMOVE ParentCompany (varchar(255))
      REMOVE City (varchar(255))
      REMOVE State (varchar(255))
      REMOVE PrimaryMillType (varchar(255))
      REMOVE SubMillType (varchar(255))
      REMOVE Status (varchar(255))
      REMOVE TL_Region (varchar(100))
      REMOVE TL_Area (varchar(100))
      REMOVE MicroMarketName (varchar(50))
      REMOVE MicroMarketID (int16)
      REMOVE Latitude (real64)
      REMOVE Longitude (real64)
      REMOVE ModifiedOn (datetime)
      REMOVE Address1 (varchar(255))
      REMOVE Address2 (varchar(255))
      REMOVE Address3 (varchar(255))
      REMOVE Country (varchar(50))
      REMOVE ZipCode (varchar(10))
      REMOVE DestinationID (varchar(50))
      REMOVE LIMSName (varchar(100))
      REMOVE MapLabel (varchar(255))
      REMOVE ForiskID (varchar(50))
      REMOVE ForiskName (varchar(200))
      REMOVE ForiskStatus (varchar(50))
      REMOVE Region (varchar(50))
      REMOVE Capacity (real64)
      REMOVE Units (varchar(50))
      REMOVE Species (varchar(50))
      REMOVE EndUse (varchar(200))
      REMOVE Demand_tons (int32)
      REMOVE RecycledPct (real64)
      REMOVE Newsprint (real64)
      REMOVE Printing_Writing (real64)
      REMOVE Household_Sanitary (real64)
      REMOVE Packaging (real64)
      REMOVE Specialty_DissolvingPulp (real64)
      REMOVE MarketPulp (real64)
      REMOVE Certification (varchar(50))
      REMOVE fme_db_operation (char(9))
    USER_EXPOSED_ATTRIBUTES = name
    -> Step2C:CreateDeleteList [Inserted]
Step2C:CreateDeleteList: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step2D:RemoveExistingNewMillsFromODPaths [INITIATOR]
    SUMMARY -> Step2C:RemoveExistingNewMillsFromODMatrix [INITIATOR]
    SUMMARY -> Step2B:RemoveExistingNewMillsMillsDrive [INITIATOR]
    SUMMARY -> Step2A:RemoveExistingNewMillsMillsRing [INITIATOR]
Step2A:AttributeManager: AttributeManager
    ATTR_TABLE = SET_TO Name (varchar(200)) = @Value(MillID)
    USER_EXPOSED_ATTRIBUTES = name
    -> Step3:DeltaMills [Inserted]
Note: Copy and paste from DetectTest
Step3:DeltaMills: FeatureWriter
    ARCGISPORTALFEATURES_ASYNC_WRITE = NO
    ARCGISPORTALFEATURES_AUTH_TYPE = generate_token
    ARCGISPORTALFEATURES_DESTINATION_DATASETTYPE_VALIDATION = Yes
    ARCGISPORTALFEATURES_EXISTING_FEATURE_SERVICE_HANDLING = DROP_CREATE
    ARCGISPORTALFEATURES_FEATURESERVICE_NAME = MillsDelta
    ARCGISPORTALFEATURES_FEATURES_PER_REQUEST = 1000
    ARCGISPORTALFEATURES_FEATURE_SERVICE_CREATE_FILEGDB = YES
    ARCGISPORTALFEATURES_FEATURE_SERVICE_HANDLING = CREATE_IF_MISSING
    ARCGISPORTALFEATURES_FEATURE_SERVICE_SELECTION_SOURCE = User
    ARCGISPORTALFEATURES_FOLDER_NAME = FIRST_FME_MILL
    ARCGISPORTALFEATURES_PASSWORD =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
    ARCGISPORTALFEATURES_TARGET_WKID = 102100
    ARCGISPORTALFEATURES_USER = svc-fme
    ARCGISPORTALFEATURES_USE_BRANCH_VERSIONING = NO
    ARCGISPORTALFEATURES_USE_GLOBAL_ID = No
    ARCGISPORTALFEATURES_VERIFY_HTTPS = Yes
    DATASET = https://webgis-uat.weyer.com/gisportal
    DATASET_ATTR = _dataset
    FEATURE_TYPE_LIST_ATTR = _feature_types
    FORMAT = ARCGISPORTALFEATURES
    TOTAL_FEATURES_WRITTEN_ATTR = _total_features_written
    SUMMARY -> Step4:_Do_we_need_to_calculate_Drive_Times
Note: SUGGESTION - change to topic notification
Step4:_Do_we_need_to_calculate_Drive_Times: Tester
    BOOL_OP = OR
    TEST_CLAUSE = TEST @Value(_total_features_written) > 0
    TEST_MODE = TEST
    PASSED -> FMEFlowNotifier
    FAILED -> No_Mills_Terminator
FMEFlowNotifier
    BODY = Features written: @Value(_total_features_written)
    SERVER_CONNECTION = mccunee FME Flow
    TOPIC = MILL_CHANGE_DETECTION
No_Mills_Terminator: Terminator
    MESSAGE = Translation Terminated No mills to create drive times with.

Bookmark: Needed for this setup when using gdb
Mills_UsedForDeleteTests (reader GEODATABASE_FILE_2) [off]
    attributes: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

Bookmark: Step1D:Mill Inputs
Mills (reader GEODATABASE_SDE_1)
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50)
    -> Step2:_Detect_Changes_in_Mills [ORIGINAL]
Mills_Edit_Disney (reader GEODATABASE_FILE_3)
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50)
    -> Step1E:AttributeFilter
Mills_Original (reader GEODATABASE_FILE_1) [off]
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50)
    -> Step2:_Detect_Changes_in_Mills [ORIGINAL]

Bookmark: Delete Existing Closed Mills. These tables must exist.
Step1H:RemoveExistingClosedMillsMillsRing: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".MillsRing WHERE millid IN (SELECT MillID FROM "FIRST".MillClosedList);
    RESULT -> Step2A:AttributeManager
Step1I:RemoveExistingClosedMillsMillsDrive: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".MillsDrive WHERE millid IN (SELECT MillID FROM "FIRST".MillClosedList);
    RESULT -> Step2A:AttributeManager
Step1J:RemoveExistingClosedMillsFromODMatrix: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".ODMatrix WHERE destinationname IN (SELECT CAST(MillID as real) FROM "FIRST".MillClosedList);
    RESULT -> Step2A:AttributeManager
Step1K:RemoveExistingClosedMillsFromODPaths: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".ODPaths WHERE destinationname IN (SELECT MillID FROM "FIRST".MillClosedList);
    RESULT -> Step2A:AttributeManager

Bookmark: Delete Existing Mills. These tables must exist.
Step2A:RemoveExistingNewMillsMillsRing: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".MillsRing WHERE millid IN (SELECT MillID FROM "FIRST".MillDeleteList);
Step2B:RemoveExistingNewMillsMillsDrive: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".MillsDrive WHERE millid IN (SELECT MillID FROM "FIRST".MillDeleteList);
Step2C:RemoveExistingNewMillsFromODMatrix: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".ODMatrix WHERE destinationname IN (SELECT CAST(MillID as real) FROM "FIRST".MillDeleteList);
Step2D:RemoveExistingNewMillsFromODPaths: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".ODPaths WHERE destinationname IN (SELECT MillID FROM "FIRST".MillDeleteList);
