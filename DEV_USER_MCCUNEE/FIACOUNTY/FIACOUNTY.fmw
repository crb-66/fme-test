FME workspace FIACOUNTY.fmw

Readers:
- SNOWFLAKE_NONSPATIAL_1: SNOWFLAKE_NONSPATIAL from $(DEV_CDO_SNOWFLAKE)
- GEODATABASE_SDE_1: GEODATABASE_SDE from FME-ILS-DEV-RO-V2

Writers:
- GEODATABASE_SDE_6: GEODATABASE_SDE to TLDEVDBSFRS01_FIRST_FIRSTDW_Editor_V2

Bookmark: READER
FACT_GROWTH_DRAIN_REMOVALS (reader SNOWFLAKE_NONSPATIAL_1)
    attributes: ACRES number(26,2), COUNTY_ID varchar(4), EVALUATION_GROUP_CODE number(10,0), FOREST_TYPE_ID varchar(4), FIBER_GROWTH number(31,5), FIBER_REMOVAL number(31,5), FIBER_VOLUME number(31,5), GROWTH number(29,5), GROWTH_GRADE number(30,5), OWNERSHIP_CLASS varchar(7), PLOT_COUNT number(5,0), REMOVAL number(29,5), REMOVAL_GRADE number(30,5), STAND_AGE_ID varchar(4), VOLUME number(29,5), VOLUME_GRADE number(30,5), SNOWFLAKE_LAST_UPDATED_DATE timestamp_ntz
    -> FIA_SCHEMATIC [LEFT]
DIM_COUNTY (reader SNOWFLAKE_NONSPATIAL_1)
    attributes: COUNTY_ID varchar(4), COUNTY_CODE varchar(5), COUNTY_NAME varchar(300), STATE_FIPS_CODE varchar(2), STATE_ABBREVIATION varchar(2)
    -> FIA_SCHEMATIC [RIGHT]
County (reader GEODATABASE_SDE_1)
    attributes: OBJECTID integer, StateName char(50), StateCode char(2), StateFip char(2), CountyName char(50), CountyFip char(3), StateCountyFip char(5), Shape.STArea() double, Shape.STLength() double
    -> MAKE_VALUES_UPPER

Bookmark: TRANSFORM_SPATIAL_ENRICHMENT
FIA_SCHEMATIC: FeatureJoiner
    ATTR_CONFLICT_RES = Prefer Left
    GEOMETRY_HANDLING = Prefer Left
    JOIN_KEYS = COUNTY_ID COUNTY_ID AUTO
    JOIN_MODE = Inner
    JOINED -> SPATIALLY_ENRICH [LEFT]
MAKE_VALUES_UPPER: StringCaseChanger
    ATTRCHOICE = SELECTED
    ATTRLIST = CountyName StateCode StateName
    CHANGE_TYPE = upper
    -> SPATIALLY_ENRICH [RIGHT]
SPATIALLY_ENRICH: FeatureJoiner
    ATTR_CONFLICT_RES = Prefer Left
    GEOMETRY_HANDLING = Prefer Right
    JOIN_KEYS = COUNTY_NAME CountyName AUTO COUNTY_CODE StateCountyFip AUTO
    JOIN_MODE = Full
    JOINED -> MAKE_COLUMNS_UPPER
MAKE_COLUMNS_UPPER: BulkAttributeRenamer
    ATTRCHOICE = Selected Attributes
    ATTRLIST = ACRES COUNTY_CODE COUNTY_ID COUNTY_NAME CountyFip CountyName EVALUATION_GROUP_CODE FIBER_GROWTH FIBER_REMOVAL FIBER_VOLUME FOREST_TYPE_ID GROWTH GROWTH_GRADE OBJECTID OWNERSHIP_CLASS PLOT_COUNT REMOVAL REMOVAL_GRADE SNOWFLAKE_LAST_UPDATED_DATE STAND_AGE_ID STATE_ABBREVIATION STATE_FIPS_CODE StateCode StateCountyFip StateFip StateName VOLUME VOLUME_GRADE
    CASE_CHANGE_TYPE = upper
    MODE_CHOICE = RENAME
    PATTERN_ACTION_DISP = CASECHANGE
    -> FIACOUNTY (writer GEODATABASE_SDE_6)

Bookmark: WRITER
FIACOUNTY (writer GEODATABASE_SDE_6)
    attributes: ACRES double(25,10), EVALUATION_GROUP_CODE bigint, FOREST_TYPE_ID char(4), FIBER_GROWTH double(30,12), FIBER_REMOVAL double(30,12), FIBER_VOLUME double(30,12), GROWTH double(28,12), GROWTH_GRADE double(29,12), OWNERSHIP_CLASS char(7), PLOT_COUNT integer, REMOVAL double(28,12), REMOVAL_GRADE double(29,12), STAND_AGE_ID char(4), VOLUME double(28,12), VOLUME_GRADE double(29,12), SNOWFLAKE_LAST_UPDATED_DATE date, STATE_ABBREVIATION char(2), OBJECTID integer, STATENAME char(50), STATECODE char(2), STATEFIP char(2), COUNTYNAME char(50), COUNTYFIP char(3), STATECOUNTYFIP char(5), Shape_STArea__ double, Shape_STLength__ double

Bookmark: Asset Description
Note: Use this data to generate FIA data that is spatially enriched with county boundaries, THIS IS A CHANGE I MADE. / COMMIT 1 / COMMIT 2 / COMMIT 3
