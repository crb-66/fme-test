FME workspace META_BUILDER.fmw

Parameters:
- SourceDataset_FMW = \\tltstapgisfme01\FME_Flow_Share\repositories\DEV\FIACOUNTY\FIACOUNTY.fmw   # Source FME Workspace (FMW) File
- ROOTNAME:   # Python Script
      import os
      
      return os.path.basename(FME_MacroValues['SourceDataset_FMW']).replace(".fmw", ".json")
- DestDataset_JSON = \\tltstapgisfme01\FME_Flow_Share\resources\data\PIPELINE_METADATA\$(ROOTNAME)   # Destination JSON (JavaScript Object Notation) File

Readers:
- FMW_1: FMW from $(SourceDataset_FMW)

Writers:
- TEXTLINE_1: TEXTLINE to $(DestDataset_JSON)

Bookmark: gen_filename
Note: trying to figure out how to dynamically set the filename path
Creator_2 [off]
    GEOMTYPE = Geometry Object
    NUM = 1
    CREATED -> FilenamePartExtractor
FilenamePartExtractor [off]
    DIRNAME_ATTR = _dirname
    DIRPATH_ATTR = _dirpath
    EXTENSION_ATTR = _extension
    FULLNAME_ATTR = _filename
    ROOTNAME_ATTR = _rootname
    SRC_ATTR = $(SourceDataset_FMW)
    -> AttributeCreator
AttributeCreator [off]
    ATTR_TABLE = SET_TO _rootname (buffer) = @Value(_rootname)

Bookmark: REQUIRED_METADATA_ATTRIBUTES
ReaderFeatureTypes (reader FMW_1)
    attributes: workspace_id uint32, reader_id string, feature_type_id uint32, reader_feature_type_qualifier string, reader_feature_type_name string, reader_feature_type_possible_geometries string, reader_feature_type_enabled logical
    -> JSONTemplater [READERFEATURETYPES]
WriterFeatureTypes (reader FMW_1)
    attributes: workspace_id uint32, writer_id string, feature_type_id uint32, writer_feature_type_qualifier string, writer_feature_type_name string, writer_feature_type_possible_geometries string, writer_feature_type_enabled logical
    -> JSONTemplater [WRITERFEATURETYPES]
Connections (reader FMW_1)
    attributes: workspace_id uint32, custom_transformer_parent_name string, connection_id uint32, connection_source_id uint32, connection_target_id uint32, connection_source_port_desc string, connection_target_port_desc string, connection_enabled logical, connection_execution_index uint32, connection_hidden logical
    -> JSONTemplater [CONNECTIONS]
FileProperties (reader FMW_1)
    attributes: workspace_id uint32, file_path string, file_size uint64, creation_date datetime, modified_date datetime, last_run_date datetime, password_protected logical
    -> JSONTemplater [PIPELINEPROPERTIES]
Bookmarks (reader FMW_1)
    attributes: workspace_id uint32, custom_transformer_parent_name string, bookmark_id uint32, bookmark_name string, bookmark_description string, bookmark_contents string
    -> JSONTemplater [BOOKMARKS]
    -> PurviewMetadataFilters
Annotations (reader FMW_1)
    attributes: workspace_id uint32, custom_transformer_parent_name string, annotation_id uint32, annotation string, annotation_type string
    -> AttributeFilter

Bookmark: AnnotationsForPurviewExtractor
PurviewMetadataFilters: AttributeFilter
    ATTR_NAME = bookmark_name
    ATTR_VALUES = <Empty>,Asset Description,<Missing>,<Null>,<Unfiltered>
    Asset Description -> AttributeFilter
AttributeFilter
    ATTR_NAME = annotation_id
    ATTR_VALUES = <Empty>,<Missing>,<Null>,<Unfiltered>,19
    19 -> HTMLExtractor
HTMLExtractor
    _FME_USE_PARSER = html.parser
    _FME_VERIFY_HTTPS = yes
    ___fme_htmlex_html_field = @Value(annotation)
    ___fme_htmlex_html_specification = Content
    ___fme_htmlex_result_type_name = LIST_ATTR
    ___fme_htmlex_search_table = Asset_Description p Value
    Results -> ListConcatenator
ListConcatenator
    DROP_EMPTY_PARTS = Yes
    LIST_ATTR = Asset_Description{}
    SEP = ,
    VAL_ATTR = Asset_Description
    -> JSONTemplater [PIPELINEPROPERTIES]

Bookmark: AVAILABLE_METADATA_ATTRIBUTES
Breakpoints (reader FMW_1)
    attributes: workspace_id uint32, custom_transformer_parent_name string, breakpoint_id uint32, breakpoint_name string, breakpoint_condition string, breakpoint_test_clause string, breakpoint_enabled logical
FeatureTypeFormatAttributes (reader FMW_1)
    attributes: workspace_id uint32, feature_type_id uint32, format_attribute_name string, format_attribute_type string
FeatureTypeParameters (reader FMW_1)
    attributes: workspace_id uint32, feature_type_id uint32, feature_type_parameter_name string, feature_type_parameter_value string
FeatureTypeUserAttributes (reader FMW_1)
    attributes: workspace_id uint32, feature_type_id uint32, user_attribute_name string, user_attribute_type string, user_attribute_exposed logical
PublishedParameters (reader FMW_1)
    attributes: workspace_id uint32, custom_transformer_parent_name string, published_parameter_name string, published_parameter_type string, published_parameter_default_value string, published_parameter_containing_group string
ReaderHistogram (reader FMW_1)
    attributes: workspace_id uint32, reader_type string, reader_count uint32
ReaderParameters (reader FMW_1)
    attributes: workspace_id uint32, reader_id string, reader_parameter_name string, reader_parameter_value string
Readers (reader FMW_1)
    attributes: workspace_id uint32, reader_id string, reader_name string, reader_keyword string, reader_type string, source_dataset string, reader_enabled logical, reader_generate_build_number uint32
Note: Statistics: FIACOUNTY [FMW] possibly useful for debugging and accuracy
Statistics (reader FMW_1)
    attributes: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
TransformerHistogram (reader FMW_1)
    attributes: workspace_id uint32, transformer_type string, transformer_count uint32
TransformerOutputPortAttributes (reader FMW_1)
    attributes: workspace_id uint32, custom_transformer_parent_name string, transformer_id uint32, transformer_output_port_id string, transformer_output_port_attribute_name string, transformer_output_port_attribute_constant_value string, transformer_output_port_attribute_enabled string
TransformerOutputPorts (reader FMW_1)
    attributes: workspace_id uint32, custom_transformer_parent_name string, transformer_id uint32, transformer_output_port_id string, transformer_output_port_name string
TransformerParameters (reader FMW_1)
    attributes: workspace_id uint32, custom_transformer_parent_name string, transformer_id uint32, transformer_parameter_name string, transformer_parameter_value string
Transformers (reader FMW_1)
    attributes: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
UserParameters (reader FMW_1)
    attributes: workspace_id uint32, custom_transformer_parent_name string, user_parameter_name string, user_parameter_definition string, user_parameter_parent_group string, user_parameter_default_value string
UserParameterStructures (reader FMW_1)
    attributes: workspace_id uint32, custom_transformer_parent_name string, structure_definition string
WorkspaceProperties (reader FMW_1)
    attributes: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
WriterHistogram (reader FMW_1)
    attributes: workspace_id uint32, writer_type string, writer_count uint32
WriterParameters (reader FMW_1)
    attributes: workspace_id uint32, writer_id string, writer_parameter_name string, writer_parameter_value string
Writers (reader FMW_1)
    attributes: workspace_id uint32, writer_id string, writer_name string, writer_keyword string, writer_type string, destination_dataset string, writer_enabled logical, writer_generate_build_number uint32

Bookmark: TRANSFORMERS
Creator
    GEOMTYPE = Geometry Object
    NUM = 1
    CREATED -> JSONTemplater [ROOT]
JSONTemplater
    BOOKMARKS_QUERY_EXPR:
      {
          "bookmark_id": fme:get-attribute("bookmark_id"),
          "bookmark_name": fme:get-attribute("bookmark_name"),
          "bookmark_contents": fme:get-attribute("bookmark_contents"),
          "bookmark_description": fme:get-attribute("bookmark_description")
      }
    CONNECTIONS_QUERY_EXPR:
      {
          "workspace_id": fme:get-attribute("workspace_id"),
          "custom_transformer_parent_name": fme:get-attribute("custom_transformer_parent_name"),
          "connection_id": fme:get-attribute("connection_id"),
          "connection_source_id": fme:get-attribute("connection_source_id"),
          "connection_target_id": fme:get-attribute("connection_target_id"),
          "connection_source_port_desc": fme:get-attribute("connection_source_port_desc"),
          "connection_target_port_desc": fme:get-attribute("connection_target_port_desc"),
          "connection_enabled": fme:get-attribute("connection_enabled"),
          "connection_execution_index": fme:get-attribute("connection_execution_index"),
          "connection_hidden": fme:get-attribute("connection_hidden"),
          "fme_dataset": fme:get-attribute("fme_dataset")
      }
    PIPELINEPROPERTIES_QUERY_EXPR:
      {
          "workspace_id": fme:get-attribute("workspace_id"),
          "file_path": fme:get-attribute("file_path"),
          "creation_date": fme:get-attribute("creation_date"),
          "modified_date": fme:get-attribute("modified_date"),
          "last_run_date": fme:get-attribute("last_run_date"),
          "password_protected": fme:get-attribute("password_protected"),
          "fme_dataset": fme:get-attribute("fme_dataset"),
          "asset_description": fme:get-attribute("Asset_Description")
      }
    READERFEATURETYPES_QUERY_EXPR:
      {
          "workspace_id": fme:get-attribute("workspace_id"),
          "reader_id": fme:get-attribute("reader_id"),
          "feature_type_id": fme:get-attribute("feature_type_id"),
          "reader_feature_type_qualifier": fme:get-attribute("reader_feature_type_qualifier"),
          "reader_feature_type_name": fme:get-attribute("reader_feature_type_name"),
          "reader_feature_type_possible_geometries": fme:get-attribute("reader_feature_type_possible_geometries"),
          "reader_feature_type_enabled": fme:get-attribute("reader_feature_type_enabled")
       }
    RESULT_ATTRIBUTE = _result
    ROOT_QUERY_EXPR:
      {
          "ReaderFeatureTypes": fme:process-features("READERFEATURETYPES"),
          "WriterFeatureTypes": fme:process-features("WRITERFEATURETYPES"),
          "Connections": fme:process-features("CONNECTIONS")
      }
    VISIBLE_QUERY_VALIDATE = Yes
    WRITERFEATURETYPES_QUERY_EXPR:
      {
          "workspace_id": fme:get-attribute("workspace_id"),
          "writer_id": fme:get-attribute("writer_id"),
          "feature_type_id": fme:get-attribute("feature_type_id"),
          "writer_feature_type_qualifier": fme:get-attribute("writer_feature_type_qualifier"),
          "writer_feature_type_name": fme:get-attribute("writer_feature_type_name"),
          "writer_feature_type_possible_geometries": fme:get-attribute("writer_feature_type_possible_geometries"),
          "writer_feature_type_enabled": fme:get-attribute("writer_feature_type_enabled")
       }
    -> text_line (writer TEXTLINE_1)

Bookmark: WRITERS
Note: : META_WRITER: todo need to determine correct output of json file to send for API web connection
text_line (writer TEXTLINE_1)
    attributes: text_line_data buffer

Bookmark: READERS
Note: The reader is a FMW workbench reader with "all attributes" selected
