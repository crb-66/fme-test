FME workspace ILS_County.fmw

Parameters:
- SourceDataset_GEODATABASE_SDE_2 = TLDEVILSDBS10_FME_BASEDATA_RO   # ArcSDE Geodatabase Connection
- SourceDataset_MSSQL_SPATIAL_3 = ILSDV-UAT-RO   # SQL Server Connection
- SourceDataset_SQLITE3 = D:\Temp\FIA\SQLite_FIADB_GA\SQLite_FIADB_GA.db   # SQLite Database
- DestDataset_GEODATABASE_SDE = TLDEVDBSFRS01_ETL_FIRSTStaging_Editor   # ArcSDE Geodatabase Connection

Readers:
- GEODATABASE_SDE_3: GEODATABASE_SDE from $(SourceDataset_GEODATABASE_SDE_2)
- MSSQL_SPATIAL_2: MSSQL_SPATIAL from $(SourceDataset_MSSQL_SPATIAL_3)
- SQLITE3_1: SQLITE3 from $(SourceDataset_SQLITE3)

Writers:
- GEODATABASE_SDE_1: GEODATABASE_SDE to $(DestDataset_GEODATABASE_SDE)

County (reader MSSQL_SPATIAL_2)
    attributes: OBJECTID integer, StateName varchar(50), StateCode varchar(2), StateFip varchar(2), CountyName varchar(50), CountyFip varchar(3), StateCountyFip varchar(5)
    -> FeatureJoiner [LEFT]
Note: One State Example
COUNTY (reader SQLITE3_1)
    attributes: STATECD integer,Unique, UNITCD integer,Unique, COUNTYCD integer,Unique, COUNTYNM varchar(50), CN varchar(34),Unique, CREATED_BY varchar(30), CREATED_DATE text, CREATED_IN_INSTANCE varchar(6), MODIFIED_BY varchar(30), MODIFIED_DATE text, MODIFIED_IN_INSTANCE varchar(6)
    -> AttributeCreator
AttributeCreator
    ATTR_TABLE = SET_TO StateCountyFip (varchar(5)) = @PadLeft(@Value(STATECD),2,0)@PadLeft(@Value(COUNTYCD),3,0)
    -> FeatureJoiner [RIGHT]
FeatureJoiner
    ATTR_CONFLICT_RES = Prefer Left
    GEOMETRY_HANDLING = Prefer Left
    JOIN_KEYS = StateCountyFip StateCountyFip AUTO
    JOIN_MODE = Inner
    JOINED -> FIA_FME_Join_Test (writer GEODATABASE_SDE_1)
FIA_FME_Join_Test (writer GEODATABASE_SDE_1)
    attributes: OBJECTID integer, StateName char(50), StateCode char(2), StateFip char(2), CountyName char(50), CountyFip char(3), StateCountyFip char(5), STATECD bigint, UNITCD bigint, COUNTYCD bigint, COUNTYNM char(50), CN char(34), CREATED_BY char(30), CREATED_DATE char(2048), CREATED_IN_INSTANCE char(6), MODIFIED_BY char(30), MODIFIED_DATE char(2048), MODIFIED_IN_INSTANCE char(6)
