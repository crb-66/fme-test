FME workspace TotalPineRoundwoodDemand.fmw

Parameters:
- SourceDataset_SNOWFLAKE_NONSPATIAL = DEV_CDO_FME_FIRST_SRVACCT_PL_MI   # Connection
- SourceDataset_GEODATABASE_SDE = FME-ILS-DEV-RO   # ArcSDE Geodatabase Connection

Readers:
- SNOWFLAKE_NONSPATIAL_1: SNOWFLAKE_NONSPATIAL from $(SourceDataset_SNOWFLAKE_NONSPATIAL)
- GEODATABASE_SDE_1: GEODATABASE_SDE from $(SourceDataset_GEODATABASE_SDE)

FACT_MI_MILL (reader SNOWFLAKE_NONSPATIAL_1)
    attributes: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
Mills (reader GEODATABASE_SDE_1)
    attributes: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
