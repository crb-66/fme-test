FME workspace SNOWTEST.fmw

Readers:
- SNOWFLAKE_NONSPATIAL_1: SNOWFLAKE_NONSPATIAL from $(DEV_CDO_SNOWFLAKE)

Writers:
- GEODATABASE_SDE_6: GEODATABASE_SDE to TLDEVDBSFRS01_FIRST_FIRSTDW_Editor_V2

Bookmark: READERS
FACT_GROWTH_DRAIN_REMOVALS (reader SNOWFLAKE_NONSPATIAL_1)
    attributes: ACRES number(26,2), COUNTY_ID varchar(4), EVALUATION_GROUP_CODE number(10,0), FOREST_TYPE_ID varchar(4), FIBER_GROWTH number(31,5), FIBER_REMOVAL number(31,5), FIBER_VOLUME number(31,5), GROWTH number(29,5), GROWTH_GRADE number(30,5), OWNERSHIP_CLASS varchar(7), PLOT_COUNT number(5,0), REMOVAL number(29,5), REMOVAL_GRADE number(30,5), STAND_AGE_ID varchar(4), VOLUME number(29,5), VOLUME_GRADE number(30,5), SNOWFLAKE_LAST_UPDATED_DATE timestamp_ntz
    -> FIA_SCHEMATIC [LEFT]
DIM_COUNTY (reader SNOWFLAKE_NONSPATIAL_1)
    attributes: COUNTY_ID varchar(4), COUNTY_CODE varchar(5), COUNTY_NAME varchar(300), STATE_FIPS_CODE varchar(2), STATE_ABBREVIATION varchar(2)
    -> FIA_SCHEMATIC [RIGHT]

Bookmark: TRANSFORM_SPATIAL_ENRICHMENT
FIA_SCHEMATIC: FeatureJoiner
    ATTR_CONFLICT_RES = Prefer Left
    GEOMETRY_HANDLING = Prefer Left
    JOIN_KEYS = COUNTY_ID COUNTY_ID AUTO
    JOIN_MODE = Inner
    JOINED -> MAKE_COLUMNS_UPPER
MAKE_COLUMNS_UPPER: BulkAttributeRenamer
    ATTRCHOICE = All Attributes
    CASE_CHANGE_TYPE = upper
    MODE_CHOICE = RENAME
    PATTERN_ACTION_DISP = CASECHANGE
    -> SNOWTEST (writer GEODATABASE_SDE_6)

Bookmark: WRITER
SNOWTEST (writer GEODATABASE_SDE_6)
    attributes: ACRES double(25,10), EVALUATION_GROUP_CODE bigint, FOREST_TYPE_ID char(4), FIBER_GROWTH double(30,12), FIBER_REMOVAL double(30,12), FIBER_VOLUME double(30,12), GROWTH double(28,12), GROWTH_GRADE double(29,12), OWNERSHIP_CLASS char(7), PLOT_COUNT integer, REMOVAL double(28,12), REMOVAL_GRADE double(29,12), STAND_AGE_ID char(4), VOLUME double(28,12), VOLUME_GRADE double(29,12), SNOWFLAKE_LAST_UPDATED_DATE date, STATE_ABBREVIATION char(2)
