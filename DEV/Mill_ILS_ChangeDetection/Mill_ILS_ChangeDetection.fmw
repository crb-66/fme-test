FME workspace Mill_ILS_ChangeDetection.fmw

Parameters:
- SourceDataset_GEODATABASE_FILE = \\TLTSTAPGISFME01\FME_Share\LeonardL1\Python\ChangeDetector\MillsForChangeDetection.gdb   # File Geodatabase
- SourceDataset_GEODATABASE_FILE_4 = \\TLTSTAPGISFME01\FME_Share\LeonardL1\Python\ChangeDetector\MillsForChangeDetection.gdb   # File Geodatabase
- SourceDataset_GEODATABASE_FILE_7 = C:\Users\McCuneE\Documents\FME\Workspaces\Redo\MillsForChangeDetection.gdb   # File Geodatabase
- DestDataset_GEODATABASE_SDE = \\tltstapgisfme01\FME_Share\TLDEVDBSFRS01_FIRST_FIRSTDW_Editor.sde   # Connection File
- SourceDataset_GEODATABASE_SDE = TLDEVDBSFRS01_FIRST_FIRSTDW_Viewer.sde   # ArcSDE Geodatabase Connection

Readers:
- GEODATABASE_FILE_1: GEODATABASE_FILE from $(SourceDataset_GEODATABASE_FILE)
- GEODATABASE_FILE_3: GEODATABASE_FILE from $(SourceDataset_GEODATABASE_FILE_4)
- GEODATABASE_FILE_6: GEODATABASE_FILE from $(SourceDataset_GEODATABASE_FILE_7)
- GEODATABASE_SDE_2: GEODATABASE_SDE from $(SourceDataset_GEODATABASE_SDE)

Writers:
- GEODATABASE_SDE_1: GEODATABASE_SDE to $(DestDataset_GEODATABASE_SDE)

Creator
    GEOMTYPE = Geometry Object
    NUM = 1
    CREATED -> Step1A:_Delete_Delta_Portal_Items
Note: Python Script to Delete Mill Deltas in UAT Portal
Note: Python Code Needs work to handle Environments
Step1A:_Delete_Delta_Portal_Items: SystemCaller
    ATTR = python_exitcode
    CMD = E:\Projects\PythonProEnv\python.exe "\\TLTSTAPGISFME01\FME_Share\LeonardL1\Python\ChangeDetector\DeltaDeletePortalLayers.py"
    -> Step1B:Tester
Step1B:Tester: Tester
    BOOL_OP = OR
    TEST_CLAUSE = TEST @Value(python_exitcode) = 0
    TEST_MODE = TEST
    PASSED -> Step2:_Detect_Changes_in_Mills [ORIGINAL]
    FAILED -> Step1C:Portal_Delete_Terminator
Step1C:Portal_Delete_Terminator: Terminator
    MESSAGE = Translation Terminated due to errors with deleting portal items.
Note: Check values, as I've seen open vs Open etc. Mills data needs to be cleaned and Status checked with QA
Step1E:AttributeFilter: AttributeFilter
    ATTR_NAME = Status
    ATTR_VALUES = <Empty>,Unknown,Open,Closed,Announced,Under Construction,<Missing>,Idle,NA,open,<Null>,<Unfiltered>
    Unknown -> Step2:_Detect_Changes_in_Mills [REVISED]
    Open -> Step2:_Detect_Changes_in_Mills [REVISED]
    Closed -> Step1F:AttributeManager
    Announced -> Step2:_Detect_Changes_in_Mills [REVISED]
    Under Construction -> Step2:_Detect_Changes_in_Mills [REVISED]
    Idle -> Step2:_Detect_Changes_in_Mills [REVISED]
    NA -> Step2:_Detect_Changes_in_Mills [REVISED]
    open -> Step2:_Detect_Changes_in_Mills [REVISED]
Step1F:AttributeManager: AttributeManager
    ATTR_TABLE:
      REMOVE OBJECTID (int32)
      REMOVE Source (varchar(255))
      SET_TO MillID (char(8)) = @Value(MillID)
      REMOVE MillName (varchar(255))
      REMOVE ParentCompany (varchar(255))
      REMOVE City (varchar(255))
      REMOVE State (varchar(255))
      REMOVE PrimaryMillType (varchar(255))
      REMOVE SubMillType (varchar(255))
      REMOVE Status (varchar(255))
      REMOVE TL_Region (varchar(100))
      REMOVE TL_Area (varchar(100))
      REMOVE MicroMarketName (varchar(50))
      REMOVE MicroMarketID (int16)
      REMOVE Latitude (real64)
      REMOVE Longitude (real64)
      REMOVE ModifiedOn (datetime)
      REMOVE Address1 (varchar(255))
      REMOVE Address2 (varchar(255))
      REMOVE Address3 (varchar(255))
      REMOVE Country (varchar(50))
      REMOVE ZipCode (varchar(10))
      REMOVE DestinationID (varchar(50))
      REMOVE LIMSName (varchar(100))
      REMOVE MapLabel (varchar(255))
      REMOVE ForiskID (varchar(50))
      REMOVE ForiskName (varchar(200))
      REMOVE ForiskStatus (varchar(50))
      REMOVE Region (varchar(50))
      REMOVE Capacity (real64)
      REMOVE Units (varchar(50))
      REMOVE Species (varchar(50))
      REMOVE EndUse (varchar(200))
      REMOVE Demand_tons (int32)
      REMOVE RecycledPct (real64)
      REMOVE Newsprint (real64)
      REMOVE Printing_Writing (real64)
      REMOVE Household_Sanitary (real64)
      REMOVE Packaging (real64)
      REMOVE Specialty_DissolvingPulp (real64)
      REMOVE MarketPulp (real64)
      REMOVE Certification (varchar(50))
    USER_EXPOSED_ATTRIBUTES = name,OBJECTID,Source,MillID,MillName,ParentCompany,City,State,PrimaryMillType,SubMillType,Status,TL_Region,TL_Area,MicroMarketName,MicroMarketID,Latitude,Longitude,ModifiedOn,Address1,Address2,Address3,Country,ZipCode,DestinationID,LIMSName,MapLabel,ForiskID,ForiskName,ForiskStatus,Region,Capacity,Units,Species,EndUse,Demand_tons,RecycledPct,Newsprint,Printing_Writing,Household_Sanitary,Packaging,Specialty_DissolvingPulp,MarketPulp,Certification
    -> Step1G:CreateClosedList [Inserted]
Step1G:CreateClosedList: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step1H:RemoveExistingClosedMillsMillsRing [INITIATOR]
    SUMMARY -> Step1I:RemoveExistingClosedMillsMillsDrive [INITIATOR]
    SUMMARY -> Step1J:RemoveExistingClosedMillsFromODMatrix [INITIATOR]
    SUMMARY -> Step1K:RemoveExistingClosedMillsFromODPaths [INITIATOR]
Step2:_Detect_Changes_in_Mills: ChangeDetector
    BLANK_AND_MISSING_DIFFER = Yes
    CHECK_COORDINATE_SYSTEMS = No
    CHECK_TYPES_AND_ENCODINGS = Yes
    LENIENT_MATCH = No
    MATCH = 2D
    MATCHATTRS = MillID Latitude Longitude
    MATCH_STRATEGY = Match Selected Attributes
    PREEMPTIVE_ATTRS = MillID
    UNCHANGED_OUTPUT = Output Revised
    UPSERT_MODE = No
    INSERTED -> Step2B:AttributeManager
    INSERTED -> Step2A:AttributeManager
Step2B:AttributeManager: AttributeManager
    ATTR_TABLE:
      REMOVE OBJECTID (int32)
      REMOVE Source (varchar(255))
      RENAME_SET_VALUE MillID (char(8)) = @Value(MillID)
      REMOVE MillName (varchar(255))
      REMOVE ParentCompany (varchar(255))
      REMOVE City (varchar(255))
      REMOVE State (varchar(255))
      REMOVE PrimaryMillType (varchar(255))
      REMOVE SubMillType (varchar(255))
      REMOVE Status (varchar(255))
      REMOVE TL_Region (varchar(100))
      REMOVE TL_Area (varchar(100))
      REMOVE MicroMarketName (varchar(50))
      REMOVE MicroMarketID (int16)
      REMOVE Latitude (real64)
      REMOVE Longitude (real64)
      REMOVE ModifiedOn (datetime)
      REMOVE Address1 (varchar(255))
      REMOVE Address2 (varchar(255))
      REMOVE Address3 (varchar(255))
      REMOVE Country (varchar(50))
      REMOVE ZipCode (varchar(10))
      REMOVE DestinationID (varchar(50))
      REMOVE LIMSName (varchar(100))
      REMOVE MapLabel (varchar(255))
      REMOVE ForiskID (varchar(50))
      REMOVE ForiskName (varchar(200))
      REMOVE ForiskStatus (varchar(50))
      REMOVE Region (varchar(50))
      REMOVE Capacity (real64)
      REMOVE Units (varchar(50))
      REMOVE Species (varchar(50))
      REMOVE EndUse (varchar(200))
      REMOVE Demand_tons (int32)
      REMOVE RecycledPct (real64)
      REMOVE Newsprint (real64)
      REMOVE Printing_Writing (real64)
      REMOVE Household_Sanitary (real64)
      REMOVE Packaging (real64)
      REMOVE Specialty_DissolvingPulp (real64)
      REMOVE MarketPulp (real64)
      REMOVE Certification (varchar(50))
      REMOVE fme_db_operation (char(9))
    USER_EXPOSED_ATTRIBUTES = name
    -> Step2C:CreateDeleteList [Inserted]
Step2C:CreateDeleteList: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step2D:RemoveExistingNewMillsFromODPaths [INITIATOR]
    SUMMARY -> Step2C:RemoveExistingNewMillsFromODMatrix [INITIATOR]
    SUMMARY -> Step2B:RemoveExistingNewMillsMillsDrive [INITIATOR]
    SUMMARY -> Step2A:RemoveExistingNewMillsMillsRing [INITIATOR]
Step2A:AttributeManager: AttributeManager
    ATTR_TABLE = SET_TO Name (varchar(200)) = @Value(MillID)
    USER_EXPOSED_ATTRIBUTES = name
    -> Step3:DeltaMills [Inserted]
Note: Copy and paste from DetectTest
Step3:DeltaMills: FeatureWriter
    ARCGISPORTALFEATURES_ASYNC_WRITE = NO
    ARCGISPORTALFEATURES_AUTH_TYPE = generate_token
    ARCGISPORTALFEATURES_DESTINATION_DATASETTYPE_VALIDATION = Yes
    ARCGISPORTALFEATURES_EXISTING_FEATURE_SERVICE_HANDLING = DROP_CREATE
    ARCGISPORTALFEATURES_FEATURESERVICE_NAME = MillsDelta
    ARCGISPORTALFEATURES_FEATURES_PER_REQUEST = 1000
    ARCGISPORTALFEATURES_FEATURE_SERVICE_CREATE_FILEGDB = YES
    ARCGISPORTALFEATURES_FEATURE_SERVICE_HANDLING = CREATE_IF_MISSING
    ARCGISPORTALFEATURES_FEATURE_SERVICE_SELECTION_SOURCE = User
    ARCGISPORTALFEATURES_FOLDER_NAME = FIRST_FME_MILL
    ARCGISPORTALFEATURES_PASSWORD =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
    ARCGISPORTALFEATURES_TARGET_WKID = 102100
    ARCGISPORTALFEATURES_USER = svc-fme
    ARCGISPORTALFEATURES_USE_BRANCH_VERSIONING = NO
    ARCGISPORTALFEATURES_USE_GLOBAL_ID = No
    ARCGISPORTALFEATURES_VERIFY_HTTPS = Yes
    DATASET = https://webgis-uat.weyer.com/gisportal
    DATASET_ATTR = _dataset
    FEATURE_TYPE_LIST_ATTR = _feature_types
    FORMAT = ARCGISPORTALFEATURES
    TOTAL_FEATURES_WRITTEN_ATTR = _total_features_written
    SUMMARY -> Step4:_Do_we_need_to_calculate_Drive_Times
Step4:_Do_we_need_to_calculate_Drive_Times: Tester
    BOOL_OP = OR
    TEST_CLAUSE = TEST @Value(_total_features_written) > 0
    TEST_MODE = TEST
    PASSED -> Step5A_DriveTimeAreas
    PASSED -> Step6A_DriveTimeRings
    PASSED -> Step8A_OD_Matrix
    FAILED -> No_Mills_Terminator
No_Mills_Terminator: Terminator
    MESSAGE = Translation Terminated No mills to create drive times with.
Tester_2
    BOOL_OP = OR
    TEST_CLAUSE = TEST @Value(_total_features_written) > 2
    TEST_MODE = TEST
    PASSED -> Read_ILS_Mills_from_UAT [INITIATOR]

Bookmark: Needed for this setup when using gdb
Mills_UsedForDeleteTests (reader GEODATABASE_FILE_3) [off]
    attributes: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

Bookmark: Step1D:Mill Inputs
Mills (reader GEODATABASE_SDE_2)
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50)
    -> Step2:_Detect_Changes_in_Mills [ORIGINAL]
Note: This will be the version in ILS
Note: Keep For debugging
Mills_Edit_Disney (reader GEODATABASE_FILE_6)
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50)
    -> Step1E:AttributeFilter
Note: Todo, make a copy for comparison for Debugging
Mills_Original (reader GEODATABASE_FILE_1) [off]
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50)
    -> Step2:_Detect_Changes_in_Mills [ORIGINAL]

Bookmark: Delete Existing Closed Mills. These tables must exist.
Step1H:RemoveExistingClosedMillsMillsRing: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".MillsRing WHERE millid IN (SELECT MillID FROM "FIRST".MillClosedList);
    RESULT -> Step2A:AttributeManager
Step1I:RemoveExistingClosedMillsMillsDrive: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".MillsDrive WHERE millid IN (SELECT MillID FROM "FIRST".MillClosedList);
    RESULT -> Step2A:AttributeManager
Step1J:RemoveExistingClosedMillsFromODMatrix: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".ODMatrix WHERE destinationname IN (SELECT CAST(MillID as real) FROM "FIRST".MillClosedList);
    RESULT -> Step2A:AttributeManager
Step1K:RemoveExistingClosedMillsFromODPaths: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".ODPaths WHERE destinationname IN (SELECT MillID FROM "FIRST".MillClosedList);
    RESULT -> Step2A:AttributeManager

Bookmark: Delete Existing Mills. These tables must exist.
Step2A:RemoveExistingNewMillsMillsRing: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".MillsRing WHERE millid IN (SELECT MillID FROM "FIRST".MillDeleteList);
    RESULT -> Step2A:AttributeManager
Step2B:RemoveExistingNewMillsMillsDrive: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".MillsDrive WHERE millid IN (SELECT MillID FROM "FIRST".MillDeleteList);
    RESULT -> Step2A:AttributeManager
Step2C:RemoveExistingNewMillsFromODMatrix: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".ODMatrix WHERE destinationname IN (SELECT CAST(MillID as real) FROM "FIRST".MillDeleteList);
    RESULT -> Step2A:AttributeManager
Step2D:RemoveExistingNewMillsFromODPaths: SQLExecutor
    COMBINE_ATTRS = Result Attributes Only
    COMBINE_GEOM = Initiator Geometry Only
    DATASET = TLDEVDBSFRS01_FIRST_FIRSTDW_Editor.sde
    FORMAT = GEODATABASE_SDE
    GEODATABASE_SDE_CREATE_FEATURE_TABLES_FROM_DATA = Yes
    GEODATABASE_SDE_NAMED_CONNECTION = TLDEVDBSFRS01_FIRST_FIRSTDW_Editor.sde
    OUTPUT_FEATURES = DATA_ONLY
    SQL_STATEMENT = DELETE FROM "FIRST".ODPaths WHERE destinationname IN (SELECT MillID FROM "FIRST".MillDeleteList);
    RESULT -> Step2A:AttributeManager

Bookmark: Calculate Drive Time Areas
Note: Python Script
Step5A_DriveTimeAreas: SystemCaller
    ATTR = area_exit_code
    CMD = E:\Projects\PythonProEnv\python.exe "\\TLTSTAPGISFME01\FME_Share\LeonardL1\Python\ChangeDetector\DeltaMillDriveTimeAreas.py"
    -> Step5B:_Check_Exit_Code
Step5B:_Check_Exit_Code: Tester
    BOOL_OP = OR
    TEST_CLAUSE = TEST @Value(area_exit_code) = 0
    TEST_MODE = TEST
    PASSED -> Step5D:FeatureReader [INITIATOR]
    FAILED -> Step5C_Exit_Code_Check
Note: BEWARE Not using GUID, so that means the latest layer will not be used if more than one layer exists. Portal layers need to be deleted
Step5D:FeatureReader: FeatureReader
    ARCGISPORTALFEATURES_AUTH_TYPE = generate_token
    ARCGISPORTALFEATURES_CREATE_FEATURE_TABLES_FROM_DATA = Yes
    ARCGISPORTALFEATURES_FEATURESERVICE = svc-fme/FIRST/DeltaMillDriveTimeArea
    ARCGISPORTALFEATURES_FEATURES_PER_REQUEST = 1000
    ARCGISPORTALFEATURES_FORMAT_GUID = YES
    ARCGISPORTALFEATURES_PASSWORD =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
    ARCGISPORTALFEATURES_QUERY_FEATURE_TYPES_FOR_MERGE_FILTERS = Yes
    ARCGISPORTALFEATURES_RESOLVE_DOMAINS = No
    ARCGISPORTALFEATURES_USER = svc-fme
    ARCGISPORTALFEATURES_USE_BRANCH_VERSIONING = NO
    ARCGISPORTALFEATURES_USE_SEARCH_ENVELOPE = NO
    ARCGISPORTALFEATURES_VERIFY_HTTPS = Yes
    ATTRIBUTES = DeltaMillDriveTimeArea,"objectid,country,specialty_dissolvingpulp,source,millname,parentcompany,state,limsname,additionaldistance,longitude,marketpulp,tl_region,foriskid,micromarketid,certification,zipcode,modifiedon,tobreak,demand_tons,name,analysisarea,region,name_1,primarymilltype,maplabel,city,latitude,units,millid,capacity,household_sanitary,submilltype,recycledpct,enduse,newsprint,foriskname,address3,breaks,address2,address1,facilityoid,packaging,destinationid,frombreak,foriskstatus,tl_area,micromarketname,additionaltime,species,printing_writing,SHAPE__Length,SHAPE__Area"
    ATTR_ACCUM_MODE = Only Use Result
    COMBINE_GEOM = Use Result
    DATASET = https://webgis-uat.weyer.com/gisportal
    FORMAT = ARCGISPORTALFEATURES
    GEOMETRY_TYPES = DeltaMillDriveTimeArea,""",fme_area"""
    INTERACT = NONE
    ORDER_RESULTS = No
    OUTPUT_ADD_SCHEMA_ATTRIBUTES = NO
    OUTPUT_FEATURES_DISPLAY = Schema and Data Features
    DeltaMillDriveTimeArea -> DeltaMillsDrive (writer GEODATABASE_SDE_1)
    DeltaMillDriveTimeArea -> Step5E:FeatureWriter [Mills_Original]
    DeltaMillDriveTimeArea -> Step5I:InsertDeltaResults [Mills_Original]
Note: Store results in DW
DeltaMillsDrive (writer GEODATABASE_SDE_1) [off]
    attributes: objectid integer, country char(8), specialty_dissolvingpulp char(8), source char(8), millname char(8), parentcompany char(8), state char(8), limsname char(8), additionaldistance double, longitude char(8), marketpulp char(8), tl_region char(8), foriskid char(8), micromarketid char(8), certification char(8), zipcode char(8), modifiedon date, tobreak double, demand_tons char(8), name char(38), analysisarea double, region char(8), name_1 char(20), primarymilltype char(8), maplabel char(8), city char(8), latitude char(8), units char(8), millid char(8), capacity char(8),
      household_sanitary char(8), submilltype char(8), recycledpct char(8), enduse char(8), newsprint char(8), foriskname char(8), address3 char(8), breaks char(8), address2 char(8), address1 char(8), facilityoid integer, packaging char(8), destinationid char(8), frombreak double, foriskstatus char(8), tl_area char(8), micromarketname char(8), additionaltime double, species char(8), printing_writing char(8), SHAPE__Length double, SHAPE__Area double
Note: Assuming Layer Exists
Step5E:FeatureWriter: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step5F:_Did_Write_Succeed
Step5F:_Did_Write_Succeed: Tester
    BOOL_OP = OR
    TEST_CLAUSE = TEST @Value(_total_features_written) > 0
    TEST_MODE = TEST
    FAILED -> Step5H_Exit_Code_Check
Step5H_Exit_Code_Check: Terminator
    MESSAGE = Translation Terminated Drive time area delta write failed.
Note: Assuming Layer Exists
Step5I:InsertDeltaResults: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step5J:_Did_Write_Succeed
Step5J:_Did_Write_Succeed: Tester
    BOOL_OP = OR
    TEST_CLAUSE = TEST @Value(_total_features_written) > 0
    TEST_MODE = TEST
    PASSED -> Tester_2
    FAILED -> Step5K_Exit_Code_Check
Step5K_Exit_Code_Check: Terminator
    MESSAGE = Translation Terminated Drive time area delta write failed to Mills Drive layer
Step5C_Exit_Code_Check: Terminator
    MESSAGE = Translation Terminated Drive time areas failed.

Bookmark: Calculate Drive Time Rings
Note: Python Script
Step6A_DriveTimeRings: SystemCaller
    ATTR = mill_exit_code
    CMD = E:\Projects\PythonProEnv\python.exe "\\TLTSTAPGISFME01\FME_Share\LeonardL1\Python\ChangeDetector\DeltaMillRings.py"
    -> Step6B:_Check_Exit_Code
Step6B:_Check_Exit_Code: Tester
    BOOL_OP = OR
    TEST_CLAUSE = TEST @Value(mill_exit_code) = 0
    TEST_MODE = TEST
    PASSED -> Step6D:FeatureReader [INITIATOR]
    FAILED -> Step6C_Exit_Code_Check_2
Step6C_Exit_Code_Check_2: Terminator
    MESSAGE = Translation Terminated Drive rings failed.
Note: BEWARE Not using GUID, so that means the latest layer will not be used if more than one layer exists. Portal layers need to be deleted
Step6D:FeatureReader: FeatureReader
    ARCGISPORTALFEATURES_AUTH_TYPE = generate_token
    ARCGISPORTALFEATURES_CREATE_FEATURE_TABLES_FROM_DATA = Yes
    ARCGISPORTALFEATURES_FEATURESERVICE = svc-fme/FIRST/DeltaMillRing
    ARCGISPORTALFEATURES_FEATURES_PER_REQUEST = 1000
    ARCGISPORTALFEATURES_FORMAT_GUID = YES
    ARCGISPORTALFEATURES_PASSWORD =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
    ARCGISPORTALFEATURES_QUERY_FEATURE_TYPES_FOR_MERGE_FILTERS = Yes
    ARCGISPORTALFEATURES_RESOLVE_DOMAINS = No
    ARCGISPORTALFEATURES_USER = svc-fme
    ARCGISPORTALFEATURES_USE_BRANCH_VERSIONING = NO
    ARCGISPORTALFEATURES_USE_SEARCH_ENVELOPE = NO
    ARCGISPORTALFEATURES_VERIFY_HTTPS = Yes
    ATTRIBUTES = DeltaMillRing,"objectid,name,frombreak,tobreak,facilityoid,facilityid,name_1,source,millid,millname,parentcompany,city,state,primarymilltype,submilltype,tl_region,tl_area,micromarketname,micromarketid,latitude,longitude,modifiedon,address1,address2,address3,country,zipcode,destinationid,limsname,maplabel,foriskid,foriskname,foriskstatus,region,capacity,units,species,enduse,demand_tons,recycledpct,newsprint,printing_writing,household_sanitary,packaging,specialty_dissolvingpulp,marketpulp,certification,breaks,additionaltime,additionaldistance,SHAPE__Length,SHAPE__Area"
    ATTR_ACCUM_MODE = Only Use Result
    COMBINE_GEOM = Use Result
    DATASET = https://webgis-uat.weyer.com/gisportal
    FORMAT = ARCGISPORTALFEATURES
    GEOMETRY_TYPES = DeltaMillRing,""",fme_area"""
    INTERACT = NONE
    ORDER_RESULTS = No
    OUTPUT_ADD_SCHEMA_ATTRIBUTES = NO
    OUTPUT_FEATURES_DISPLAY = Schema and Data Features
    DeltaMillRing -> DeltaMillsRing (writer GEODATABASE_SDE_1)
    DeltaMillRing -> Step6E:FeatureWriter [Mills_Original]
    DeltaMillRing -> Step6I:InsertDeltaResults [Mills_Original]
Note: Store results in DW
DeltaMillsRing (writer GEODATABASE_SDE_1) [off]
    attributes: objectid integer, name char(40), frombreak double, tobreak double, facilityoid double, facilityid double, name_1 char(20), source char(508), millid char(508), millname char(508), parentcompany char(508), city char(508), state char(508), primarymilltype char(508), submilltype char(508), tl_region char(508), tl_area char(508), micromarketname char(508), micromarketid char(508), latitude char(508), longitude char(508), modifiedon date, address1 char(508), address2 char(508), address3 char(508), country char(508), zipcode char(508), destinationid char(508), limsname char(508), maplabel char(508),
      foriskid char(508), foriskname char(508), foriskstatus char(508), region char(508), capacity char(508), units char(508), species char(508), enduse char(508), demand_tons char(508), recycledpct char(508), newsprint char(508), printing_writing char(508), household_sanitary char(508), packaging char(508), specialty_dissolvingpulp char(508), marketpulp char(508), certification char(508), breaks char(508), additionaltime double, additionaldistance double, SHAPE__Length double, SHAPE__Area double
Note: Assuming Layer Exists
Step6E:FeatureWriter: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step6F:_Did_Write_Succeed
Step6F:_Did_Write_Succeed: Tester
    BOOL_OP = OR
    TEST_CLAUSE = TEST @Value(_total_features_written) > 0
    TEST_MODE = TEST
    FAILED -> Step6H_Exit_Code_Check
Step6H_Exit_Code_Check: Terminator
    MESSAGE = Translation Terminated Drive ring delta write failed.
Note: Assuming Layer Exists
Note: Results are appended
Step6I:InsertDeltaResults: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step6J:_Did_Write_Succeed
Step6J:_Did_Write_Succeed: Tester
    BOOL_OP = OR
    TEST_CLAUSE = TEST @Value(_total_features_written) > 0
    TEST_MODE = TEST
    PASSED -> Tester_2
    FAILED -> Step6K_Exit_Code_Check
Step6K_Exit_Code_Check: Terminator
    MESSAGE = Translation Terminated Drive Ring delta write failed to Mills Ring layer

Bookmark: Calculate OD Matrix
Note: Python Script
Step8A_OD_Matrix: SystemCaller
    ATTR = OD_exit_code
    CMD = E:\Projects\PythonProEnv\python.exe "\\TLTSTAPGISFME01\FME_Share\LeonardL1\Python\ChangeDetector\DeltaODMatrix.py"
    -> Step8B:_Check_Exit_Code
Step8B:_Check_Exit_Code: Tester
    BOOL_OP = OR
    TEST_CLAUSE = TEST @Value(OD_exit_code) = 0
    TEST_MODE = TEST
    PASSED -> Step8E:FeatureWriter [Mills_Original]
    PASSED -> Read_ILS_Mills_from_UAT [INITIATOR]
    PASSED -> Step8L:FeatureReader [INITIATOR]
    PASSED -> Step8D:FeatureReader [INITIATOR]
    FAILED -> Step8C_Exit_Code_Check
Step8C_Exit_Code_Check: Terminator
    MESSAGE = Translation Terminated OD Matrix failed.
Step8D:FeatureReader: FeatureReader
    ATTRIBUTES = CSV,"col0,OriginName,OriginOID,DestinationID,DestinationOID,DestinationName,DestinationRank,Total_Distance,Total_Time"
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = C:\Users\McCuneE\Documents\FME\Workspaces\ChangeDetector\Output\OD_Matrix.csv
    FORMAT = CSV2
    INTERACT = NONE
    ORDER_RESULTS = No
    OUTPUT_ADD_SCHEMA_ATTRIBUTES = NO
    OUTPUT_FEATURES_DISPLAY = Schema and Data Features
    CSV -> Step8E:FeatureWriter [Mills_Original]
    CSV -> Step8I:InsertDeltaResults [Mills_Original]
Step8E:FeatureWriter: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step8F:_Did_Write_Succeed
Step8F:_Did_Write_Succeed: Tester
    BOOL_OP = OR
    TEST_CLAUSE = TEST @Value(_total_features_written) > 0
    TEST_MODE = TEST
    PASSED -> Tester_2
    FAILED -> Step8H_Exit_Code_Check
Step8H_Exit_Code_Check: Terminator
    MESSAGE = Translation Terminated OD Matrix delta write failed.
Note: Results are appended
Note: Assuming Layer Exists
Note: Existing Mills deleted
Step8I:InsertDeltaResults: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step8J:_Did_Write_Succeed
Step8J:_Did_Write_Succeed: Tester
    BOOL_OP = OR
    TEST_CLAUSE = TEST @Value(_total_features_written) > 0
    TEST_MODE = TEST
    FAILED -> Step8K_Exit_Code_Check
Step8K_Exit_Code_Check: Terminator
    MESSAGE = Translation Terminated OD Matrix delta write failed to OD Matrix table
Note: Include Paths
Step8L:FeatureReader: FeatureReader
    ARCGISPORTALFEATURES_AUTH_TYPE = generate_token
    ARCGISPORTALFEATURES_CREATE_FEATURE_TABLES_FROM_DATA = Yes
    ARCGISPORTALFEATURES_FEATURESERVICE = svc-fme/FIRST_OD_MATRIX/PathDeltaODMatrix(9d7bbfee10754b5cb1507e65108f34cd)
    ARCGISPORTALFEATURES_FEATURES_PER_REQUEST = 1000
    ARCGISPORTALFEATURES_FORMAT_GUID = YES
    ARCGISPORTALFEATURES_PASSWORD =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
    ARCGISPORTALFEATURES_QUERY_FEATURE_TYPES_FOR_MERGE_FILTERS = Yes
    ARCGISPORTALFEATURES_RESOLVE_DOMAINS = No
    ARCGISPORTALFEATURES_USER = svc-fme
    ARCGISPORTALFEATURES_USE_BRANCH_VERSIONING = NO
    ARCGISPORTALFEATURES_USE_SEARCH_ENVELOPE = NO
    ARCGISPORTALFEATURES_VERIFY_HTTPS = Yes
    ATTRIBUTES = PathDeltaODMatrix,"objectid,destinationrank,total_time,total_distance,originid,originoid,originname,destinationid,destinationoid,destinationname,SHAPE__Length"
    ATTR_ACCUM_MODE = Only Use Result
    COMBINE_GEOM = Use Result
    DATASET = https://webgis-uat.weyer.com/gisportal
    FORMAT = ARCGISPORTALFEATURES
    GEOMETRY_TYPES = PathDeltaODMatrix,""",fme_line"""
    INTERACT = NONE
    ORDER_RESULTS = No
    OUTPUT_ADD_SCHEMA_ATTRIBUTES = NO
    OUTPUT_FEATURES_DISPLAY = Schema and Data Features
    PathDeltaODMatrix -> Step8M:FeatureWriter [CSV]
    PathDeltaODMatrix -> Step8P:FeatureWriter [CSV]
Note: Assuming Layer exists
Note: Results are appended
Step8P:FeatureWriter: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step8Q:_Did_Write_Succeed_3
Step8Q:_Did_Write_Succeed_3: Tester
    BOOL_OP = OR
    TEST_CLAUSE = TEST @Value(_total_features_written) > 0
    TEST_MODE = TEST
    FAILED -> Step8R_Exit_Code_Check_3
Step8R_Exit_Code_Check_3: Terminator
    MESSAGE = Translation Terminated OD Matrix delta write failed.
Step8M:FeatureWriter: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step8N:_Did_Write_Succeed_2
Step8N:_Did_Write_Succeed_2: Tester
    BOOL_OP = OR
    TEST_CLAUSE = TEST @Value(_total_features_written) > 0
    TEST_MODE = TEST
    FAILED -> Step8O_Exit_Code_Check_2
Step8O_Exit_Code_Check_2: Terminator
    MESSAGE = Translation Terminated OD Matrix delta write failed.

Bookmark: Update Stored Mills Layer in Data Warehouse
Read_ILS_Mills_from_UAT: FeatureReader
    ATTRIBUTES = dbo.Mills,"OBJECTID,Source,MillID,MillName,ParentCompany,City,State,PrimaryMillType,SubMillType,Status,TL_Region,TL_Area,MicroMarketName,MicroMarketID,Latitude,Longitude,ModifiedOn,Address1,Address2,Address3,Country,ZipCode,DestinationID,LIMSName,MapLabel,ForiskID,ForiskName,ForiskStatus,Region,Capacity,Units,Species,EndUse,Demand_tons,RecycledPct,Newsprint,Printing_Writing,Household_Sanitary,Packaging,Specialty_DissolvingPulp,MarketPulp,Certification"
    ATTR_ACCUM_MODE = Only Use Result
    COMBINE_GEOM = Use Result
    DATASET = ilsdb-uat_ILS_svc-APP_FME_RO.sde
    FEATURETYPES = dbo.Mills
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CREATE_FEATURE_TABLES_FROM_DATA = Yes
    GEODATABASE_SDE_DISABLE_FEATURE_DATASET_ATTRIBUTE = Yes
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_NAMED_CONNECTION = ilsdb-uat_ILS_svc-APP_FME_RO.sde
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_FEATURE_DATASET = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEOMETRY_TYPES = dbo.Mills,""",fme_point"""
    INTERACT = NONE
    ORDER_RESULTS = No
    OUTPUT_ADD_SCHEMA_ATTRIBUTES = NO
    OUTPUT_FEATURES_DISPLAY = Schema and Data Features
    dbo.Mills -> Mills (writer GEODATABASE_SDE_1)
    dbo.Mills -> Step7A:Update_Stored_Mills_Layer [Mills_Original]
Note: Update Stored Mills Layer
Note: Assumption that when second branch succeeds, both do.
Mills (writer GEODATABASE_SDE_1) [off]
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50)
Note: Assuming Layer Exists
Note: Step7A:Update_Stored_Mills_Layer
Step7A:Update_Stored_Mills_Layer: FeatureWriter
    DATASET = TLDEVDBSFRS01_FIRST_FIRSTDW_Editor.sde
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor.sde
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Step7B:_Did_Write_Succeed
Note: Assuming 2000 mills or more
Step7B:_Did_Write_Succeed: Tester
    BOOL_OP = OR
    TEST_CLAUSE = TEST @Value(_total_features_written) > 2000
    TEST_MODE = TEST
    FAILED -> Step7C_Exit_Code_Check
Step7C_Exit_Code_Check: Terminator
    MESSAGE = Translation Terminated Mill updated failed
