FME workspace FME_and_SDE_Tests_ESRI_ProjEng.fmw

Parameters:
- SourceDataset_GEODATABASE_SDE_2 = TLDEVDBSFRS01_ENR_FIRSTDW_Viewer   # ArcSDE Geodatabase Connection
- DestDataset_GEODATABASE_SDE = TLDEVDBSFRS01_ENR_FIRSTDW_Editor   # ArcSDE Geodatabase Connection

Readers:
- GEODATABASE_SDE_3: GEODATABASE_SDE from $(SourceDataset_GEODATABASE_SDE_2)

Writers:
- GEODATABASE_SDE_1: GEODATABASE_SDE to $(DestDataset_GEODATABASE_SDE) in USA_Contiguous_Albers_Equal_Area_Conic

State (reader GEODATABASE_SDE_3)
    attributes: OBJECTID integer, StateName char(50), StateAbbr char(2), StateFip char(2), Shape.STArea() double, Shape.STLength() double
    -> CoordinateSystemSetter
CoordinateSystemSetter
    COORDSYS = USA_Contiguous_Albers_Equal_Area_Conic
    -> StateDeployTestX2 (writer GEODATABASE_SDE_1)
StateDeployTestX2 (writer GEODATABASE_SDE_1)
    attributes: OBJECTID integer, StateName char(50), StateAbbr char(2), StateFip char(2), Shape_STArea__ double, Shape_STLength__ double
