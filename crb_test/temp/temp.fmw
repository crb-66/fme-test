FME workspace temp.fmw

Parameters:
- SourceDataset_SNOWFLAKE_NONSPATIAL = Snowflake_FIRST_DEV   # Connection

Readers:
- SNOWFLAKE_NONSPATIAL_1: SNOWFLAKE_NONSPATIAL from $(SourceDataset_SNOWFLAKE_NONSPATIAL)

FIA_GROWTH_DRAIN_REMOVALS (reader SNOWFLAKE_NONSPATIAL_1) [off]
    attributes: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
Creator [off]
    GEOMTYPE = Geometry Object
    NUM = 1
    CREATED -> HTTPCaller
HTTPCaller
    AUTH_METHOD = Web Connection
    AUTH_NAMED_CONNECTION = beaudetc1 Snowflake OAuth Token
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://sv37782.west-us-2.azure.snowflakecomputing.com/api/v2/statements/
    TRANSFER_TIMEOUT_LENGTH = 90
    UPLOAD_BODY:
      {
          "statement": "select * from SBX_TL_ILS.FME.SPATIAL_TABLE limit 10",
          "timeout": 60,
          "resultSetMetaData": {
              "format": "jsonv2"
          },
          "database": "SBX_TL_ILS",
          "schema": "FME",
          "warehouse": "SBX_CDO_FME_XS_WH",
          "role": "DEV_CDO_FME_ROLE"
      }
    UPLOAD_CONTENT_TYPE = JSON (application/json)
    UPLOAD_TYPE = Specify Upload Body
    USE_COOKIES = No
    VERIFY_SSL_CERTIFICATES = Yes
    -> HTTPCaller_Output
    <REJECTED> -> HTTPCaller__Rejected_
HTTPCaller_Output: Logger
    LOG_FEATURE = LOG_ONLY
    MAXCOORDS = 20
    MAXFEATS = 20
    MESSAGE = Feature is:
    SEVERITY = INFO
HTTPCaller__Rejected_: Logger
    LOG_FEATURE = LOG_ONLY
    MAXCOORDS = 20
    MAXFEATS = 20
    MESSAGE = Feature is:
    SEVERITY = INFO
S3Connector
    CREDENTIAL_SOURCE = System
    OPERATION_TYPE = List
    PARAMETER_SETUP = _FME_BUCKET]wy-gisservices]_FME_FILES]Imagery/]_FME_INCLUDE_SUBFOLDERS]No]_LIST_FME_ATTRIBUTES_TO_ADD]"_name _full_path _url _bucket_name _file_or_folder _file_size _file_last_modified _relative_path"]FME_CONTROLLER_QUERY_FILE]amazons3_deps1/List.fme]FME_CONTROLLER_CHOICE]List
    _FME_S3_AWS_REGION = us-west-2
    _FME_S3_REQUESTER_PAYS = no
    _FME_S3_VERIFY_SSL = yes
NoFeaturesTester
