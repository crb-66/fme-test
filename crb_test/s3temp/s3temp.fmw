FME workspace s3temp.fmw

S3Connector
    CREDENTIAL_SOURCE = Anonymous
    OPERATION_TYPE = List
    PARAMETER_SETUP = _FME_BUCKET]]_FME_FILES]]_FME_INCLUDE_SUBFOLDERS]No]_LIST_FME_ATTRIBUTES_TO_ADD]"_name _full_path _url _bucket_name _file_or_folder _file_size _file_last_modified _relative_path"]FME_CONTROLLER_QUERY_FILE]amazons3_deps1/List.fme]FME_CONTROLLER_CHOICE]List
    _FME_S3_VERIFY_SSL = Yes
