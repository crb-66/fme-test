FME workspace HeatMaps.fmw

Parameters:
- SourceDataset_GEODATABASE_SDE = TLDEVDBSFRS01_FIRST_FIRSTDW_Editor_V2   # ArcSDE Geodatabase Connection
- SourceDataset_GEODATABASE_SDE_8 = TLDEVDBSFRS01_FIRST_FIRSTDW_Editor_V2   # ArcSDE Geodatabase Connection
- SourceDataset_SNOWFLAKE_NONSPATIAL_3 = DEV_snowflake_DEV-CDO-PORTFOLIO-MANAGEMENT-PL-MI-srvacct   # Connection
- SourceDataset_SNOWFLAKE_NONSPATIAL = DEV_snowflake_QA-CDO-PORTFOLIO-MANAGEMENT-PL-MI_srvacct   # Connection

Readers:
- GEODATABASE_SDE_1: GEODATABASE_SDE from $(SourceDataset_GEODATABASE_SDE)
- GEODATABASE_SDE_5: GEODATABASE_SDE from $(SourceDataset_GEODATABASE_SDE_8)
- SNOWFLAKE_NONSPATIAL_2: SNOWFLAKE_NONSPATIAL from $(SourceDataset_SNOWFLAKE_NONSPATIAL_3)
- SNOWFLAKE_NONSPATIAL_1: SNOWFLAKE_NONSPATIAL from $(SourceDataset_SNOWFLAKE_NONSPATIAL)

FeatureJoiner_3
    ATTR_CONFLICT_RES = Prefer Left
    GEOMETRY_HANDLING = Prefer Left
    JOIN_KEYS = ILS_MILL_ID ILS_MILLS_ID AUTO
    JOIN_MODE = Inner
    JOINED -> Sorter
Sorter
    SORT_PARM = DATE_ID NATURAL DESCENDING
    SORTED -> Sampler
Sampler
    GROUP_BY = MILL_ID
    RATE = 1
    SAMPLE_MODE = No
    SAMPLE_TYPE_LONG = First N Features
    SAMPLED -> FeatureJoiner_2 [RIGHT]
Note: These SnowFlake locations require new connections when PR finalized
Note: Disney Fake, assigned real mil id north of Disney
ODMatrixFake05_01_24 (reader GEODATABASE_SDE_5)
    attributes: OBJECTID integer, col0 double, OriginName char(12), OriginOID double, DestinationID double, DestinationOID double, DestinationName double, DestinationRank double, Total_Distance double, Total_Time double, pointid integer, OriginID integer, ForestedYN smallint, ProcessingGroup smallint
    -> AttributeFilter_3
Note: Note Y/N converted
AttributeFilter_3
    ATTR_NAME = ForestedYN
    ATTR_VALUES = <Empty>,<Missing>,<Null>,<Unfiltered>,1,0
    1 -> FeatureJoiner_2 [LEFT]
FeatureJoiner_2
    ATTR_CONFLICT_RES = Prefer Left
    GEOMETRY_HANDLING = Prefer Left
    JOIN_KEYS = DestinationName MILL_ID AUTO
    JOIN_MODE = Inner
    JOINED -> AttributeManager_3
Note: Remember to reset fields when joins etc change
AttributeManager_3
    ATTR_TABLE:
      RENAME_SET_VALUE CITY > CITY2 (varchar(16777216))
      RENAME_SET_VALUE TL_AREA > TL_AREA2 (varchar(16777216))
      RENAME_SET_VALUE TL_REGION > TL_REGION2 (varchar(16777216))
    USER_EXPOSED_ATTRIBUTES = OBJECTID,col0,OriginName,OriginOID,DestinationID,DestinationOID,DestinationName,DestinationRank,Total_Distance,Total_Time,pointid,OriginID,ForestedYN,ProcessingGroup,CK,ILS_MILL_ID,FORISK_MILL_ID,MILL_CAPACITY_ID,ANNUAL_PRODUCTION_CAPACITY_FORISK,ANNUAL_PRODUCTION_CAPACITY_MI,CAPITALID_ID,DATE_ID,END_USE_ID_FORISK,HOUSEHOLD_SANITARY_FORISK,HOUSEHOLD_SANITARY_MI,MARKET_PULP_FORISK,MARKET_PULP_MI,MICROMARKET_ID,MILL_OWNER_ID_FORISK,MILL_STATUS_ID_MI,MILL_STATUS_ID_FORISK,NEWSPRINT_FORISK,NEWSPRINT_MI,OPERATING_RATE_MI,PACKAGING_FORISK,PACKAGING_MI,PRINT_WRITING_FORISK,PRINT_WRITING_MI,PRODUCT_GROUP_ID,RECYCLED_FORISK,SORTS_GROUP_ID,SPECIALTY_DISSOLVING_PULP_FORISK,SPECIALTY_DISSOLVING_PULP_MI,SPECIES_GROUP_ID,SPECIES_ID_FORISK,TL_ID,VIABILITYID_ID,WOOD_DEMAND_AT_CAPACITY_TONS_FORISK,WOOD_DEMAND_AT_CAPACITY_TONS_MI,SNOWFLAKE_LAST_UPDATED_DATE,ILS_MILLS_ID,CITY,ILS_OWNER,MILL_ID,MILL_NAME,PRIMARY_MILL_TYPE,STATE_PROVINCE,TL_AREA,TL_REGION
    -> AvgTotalDistance
    -> SumTotalDistance
    -> AvgTotalTime
    -> SumTotalTime_2
SumTotalTime_2: Aggregator
    ACCUM_ATTRS_NAME = Use Attributes From One Feature
    AGGREGATE_TYPE = Homogeneous Collection (If Possible)
    GROUP_BY = DestinationName
    MODE = Geometry - Assemble One Level
    SEP = ,
    SUM = Total_Time
    AGGREGATE -> AttributeManager_5
AttributeManager_5
    ATTR_TABLE:
      RENAME_SET_VALUE DestinationName > SumTimeDestinationName (real64)
      REMOVE Total_Distance (real64)
      REMOVE OBJECTID (int32)
      REMOVE col0 (real64)
      REMOVE OriginName (varchar(12))
      REMOVE OriginOID (real64)
      REMOVE DestinationID (real64)
      REMOVE DestinationOID (real64)
      REMOVE DestinationRank (real64)
      RENAME_SET_VALUE Total_Time > SumTotal_Time (real64)
      REMOVE pointid (int32)
      REMOVE OriginID (int32)
      REMOVE ForestedYN (int16)
      REMOVE ProcessingGroup (int16)
      REMOVE CK (varchar(16777216))
      REMOVE ILS_MILL_ID (varchar(16777216))
      REMOVE FORISK_MILL_ID (varchar(16777216))
      REMOVE MILL_CAPACITY_ID (varchar(16777216))
      REMOVE ANNUAL_PRODUCTION_CAPACITY_FORISK (number(7,1))
      REMOVE ANNUAL_PRODUCTION_CAPACITY_MI (number(38,2))
      REMOVE CAPITALID_ID (varchar(16777216))
      REMOVE DATE_ID (date)
      REMOVE END_USE_ID_FORISK (number(18,0))
      REMOVE HOUSEHOLD_SANITARY_FORISK (number(3,2))
      REMOVE HOUSEHOLD_SANITARY_MI (number(38,2))
      REMOVE MARKET_PULP_FORISK (number(5,4))
      REMOVE MARKET_PULP_MI (number(38,2))
      REMOVE MICROMARKET_ID (varchar(16777216))
      REMOVE MILL_OWNER_ID_FORISK (number(18,0))
      REMOVE MILL_STATUS_ID_MI (number(18,0))
      REMOVE MILL_STATUS_ID_FORISK (number(18,0))
      REMOVE NEWSPRINT_FORISK (number(5,4))
      REMOVE NEWSPRINT_MI (number(38,2))
      REMOVE OPERATING_RATE_MI (number(38,0))
      REMOVE PACKAGING_FORISK (number(4,3))
      REMOVE PACKAGING_MI (number(38,2))
      REMOVE PRINT_WRITING_FORISK (number(3,2))
      REMOVE PRINT_WRITING_MI (number(38,2))
      REMOVE PRODUCT_GROUP_ID (number(18,0))
      REMOVE RECYCLED_FORISK (number(3,2))
      REMOVE SORTS_GROUP_ID (number(18,0))
      REMOVE SPECIALTY_DISSOLVING_PULP_FORISK (number(3,2))
      REMOVE SPECIALTY_DISSOLVING_PULP_MI (number(38,2))
      REMOVE SPECIES_GROUP_ID (number(18,0))
      REMOVE SPECIES_ID_FORISK (number(18,0))
      REMOVE TL_ID (number(18,0))
      REMOVE VIABILITYID_ID (varchar(16777216))
      REMOVE WOOD_DEMAND_AT_CAPACITY_TONS_FORISK (number(9,0))
      REMOVE WOOD_DEMAND_AT_CAPACITY_TONS_MI (number(38,0))
      REMOVE SNOWFLAKE_LAST_UPDATED_DATE (datetime)
      REMOVE ILS_MILLS_ID (varchar(16777216))
      REMOVE CITY2 (varchar(16777216))
      REMOVE ILS_OWNER (varchar(16777216))
      REMOVE MILL_NAME (varchar(16777216))
      REMOVE PRIMARY_MILL_TYPE (varchar(16777216))
      REMOVE STATE_PROVINCE (varchar(16777216))
      REMOVE TL_AREA2 (varchar(16777216))
    USER_EXPOSED_ATTRIBUTES = DestinationName,Total_Distance,OBJECTID,col0,OriginName,OriginOID,DestinationID,DestinationOID,DestinationRank,Total_Time,pointid,OriginID,ForestedYN,ProcessingGroup,CK,ILS_MILL_ID,FORISK_MILL_ID,MILL_CAPACITY_ID,ANNUAL_PRODUCTION_CAPACITY_FORISK,ANNUAL_PRODUCTION_CAPACITY_MI,CAPITALID_ID,DATE_ID,END_USE_ID_FORISK,HOUSEHOLD_SANITARY_FORISK,HOUSEHOLD_SANITARY_MI,MARKET_PULP_FORISK,MARKET_PULP_MI,MICROMARKET_ID,MILL_OWNER_ID_FORISK,MILL_STATUS_ID_MI,MILL_STATUS_ID_FORISK,NEWSPRINT_FORISK,NEWSPRINT_MI,OPERATING_RATE_MI,PACKAGING_FORISK,PACKAGING_MI,PRINT_WRITING_FORISK,PRINT_WRITING_MI,PRODUCT_GROUP_ID,RECYCLED_FORISK,SORTS_GROUP_ID,SPECIALTY_DISSOLVING_PULP_FORISK,SPECIALTY_DISSOLVING_PULP_MI,SPECIES_GROUP_ID,SPECIES_ID_FORISK,TL_ID,VIABILITYID_ID,WOOD_DEMAND_AT_CAPACITY_TONS_FORISK,WOOD_DEMAND_AT_CAPACITY_TONS_MI,SNOWFLAKE_LAST_UPDATED_DATE,ILS_MILLS_ID,CITY2,ILS_OWNER,MILL_ID,MILL_NAME,PRIMARY_MILL_TYPE,STATE_PROVINCE,TL_AREA2,TL_REGION2
    -> FeatureJoiner_6 [RIGHT]
AvgTotalTime: Aggregator
    ACCUM_ATTRS_NAME = Use Attributes From One Feature
    AGGREGATE_TYPE = Homogeneous Collection (If Possible)
    AV = Total_Time
    GROUP_BY = DestinationName
    MODE = Geometry - Assemble One Level
    SEP = ,
    AGGREGATE -> AttributeManager_4
AttributeManager_4
    ATTR_TABLE:
      RENAME_SET_VALUE DestinationName > AvgDestinationName (real64)
      REMOVE Total_Distance (real64)
      REMOVE OBJECTID (int32)
      REMOVE col0 (real64)
      REMOVE OriginName (varchar(12))
      REMOVE OriginOID (real64)
      REMOVE DestinationID (real64)
      REMOVE DestinationOID (real64)
      REMOVE DestinationRank (real64)
      RENAME_SET_VALUE Total_Time > AvgTotal_Time (real64)
      REMOVE pointid (int32)
      REMOVE OriginID (int32)
      REMOVE ForestedYN (int16)
      REMOVE ProcessingGroup (int16)
      REMOVE CK (varchar(16777216))
      REMOVE ILS_MILL_ID (varchar(16777216))
      REMOVE FORISK_MILL_ID (varchar(16777216))
      REMOVE MILL_CAPACITY_ID (varchar(16777216))
      REMOVE ANNUAL_PRODUCTION_CAPACITY_FORISK (number(7,1))
      REMOVE ANNUAL_PRODUCTION_CAPACITY_MI (number(38,2))
      REMOVE CAPITALID_ID (varchar(16777216))
      REMOVE DATE_ID (date)
      REMOVE END_USE_ID_FORISK (number(18,0))
      REMOVE HOUSEHOLD_SANITARY_FORISK (number(3,2))
      REMOVE HOUSEHOLD_SANITARY_MI (number(38,2))
      REMOVE MARKET_PULP_FORISK (number(5,4))
      REMOVE MARKET_PULP_MI (number(38,2))
      REMOVE MICROMARKET_ID (varchar(16777216))
      REMOVE MILL_OWNER_ID_FORISK (number(18,0))
      REMOVE MILL_STATUS_ID_MI (number(18,0))
      REMOVE MILL_STATUS_ID_FORISK (number(18,0))
      REMOVE NEWSPRINT_FORISK (number(5,4))
      REMOVE NEWSPRINT_MI (number(38,2))
      REMOVE OPERATING_RATE_MI (number(38,0))
      REMOVE PACKAGING_FORISK (number(4,3))
      REMOVE PACKAGING_MI (number(38,2))
      REMOVE PRINT_WRITING_FORISK (number(3,2))
      REMOVE PRINT_WRITING_MI (number(38,2))
      REMOVE PRODUCT_GROUP_ID (number(18,0))
      REMOVE RECYCLED_FORISK (number(3,2))
      REMOVE SORTS_GROUP_ID (number(18,0))
      REMOVE SPECIALTY_DISSOLVING_PULP_FORISK (number(3,2))
      REMOVE SPECIALTY_DISSOLVING_PULP_MI (number(38,2))
      REMOVE SPECIES_GROUP_ID (number(18,0))
      REMOVE SPECIES_ID_FORISK (number(18,0))
      REMOVE TL_ID (number(18,0))
      REMOVE VIABILITYID_ID (varchar(16777216))
      REMOVE WOOD_DEMAND_AT_CAPACITY_TONS_FORISK (number(9,0))
      REMOVE WOOD_DEMAND_AT_CAPACITY_TONS_MI (number(38,0))
      REMOVE SNOWFLAKE_LAST_UPDATED_DATE (datetime)
      REMOVE ILS_MILLS_ID (varchar(16777216))
      REMOVE CITY2 (varchar(16777216))
      REMOVE ILS_OWNER (varchar(16777216))
      REMOVE MILL_NAME (varchar(16777216))
      REMOVE PRIMARY_MILL_TYPE (varchar(16777216))
      REMOVE STATE_PROVINCE (varchar(16777216))
      REMOVE TL_AREA2 (varchar(16777216))
    USER_EXPOSED_ATTRIBUTES = DestinationName,Total_Distance,OBJECTID,col0,OriginName,OriginOID,DestinationID,DestinationOID,DestinationRank,Total_Time,pointid,OriginID,ForestedYN,ProcessingGroup,CK,ILS_MILL_ID,FORISK_MILL_ID,MILL_CAPACITY_ID,ANNUAL_PRODUCTION_CAPACITY_FORISK,ANNUAL_PRODUCTION_CAPACITY_MI,CAPITALID_ID,DATE_ID,END_USE_ID_FORISK,HOUSEHOLD_SANITARY_FORISK,HOUSEHOLD_SANITARY_MI,MARKET_PULP_FORISK,MARKET_PULP_MI,MICROMARKET_ID,MILL_OWNER_ID_FORISK,MILL_STATUS_ID_MI,MILL_STATUS_ID_FORISK,NEWSPRINT_FORISK,NEWSPRINT_MI,OPERATING_RATE_MI,PACKAGING_FORISK,PACKAGING_MI,PRINT_WRITING_FORISK,PRINT_WRITING_MI,PRODUCT_GROUP_ID,RECYCLED_FORISK,SORTS_GROUP_ID,SPECIALTY_DISSOLVING_PULP_FORISK,SPECIALTY_DISSOLVING_PULP_MI,SPECIES_GROUP_ID,SPECIES_ID_FORISK,TL_ID,VIABILITYID_ID,WOOD_DEMAND_AT_CAPACITY_TONS_FORISK,WOOD_DEMAND_AT_CAPACITY_TONS_MI,SNOWFLAKE_LAST_UPDATED_DATE,ILS_MILLS_ID,CITY2,ILS_OWNER,MILL_ID,MILL_NAME,PRIMARY_MILL_TYPE,STATE_PROVINCE,TL_AREA2,TL_REGION2
    -> FeatureJoiner_5 [RIGHT]
SumTotalDistance: Aggregator
    ACCUM_ATTRS_NAME = Use Attributes From One Feature
    AGGREGATE_TYPE = Homogeneous Collection (If Possible)
    GROUP_BY = DestinationName
    MODE = Geometry - Assemble One Level
    SEP = ,
    SUM = Total_Distance
    AGGREGATE -> AttributeManager_2
AttributeManager_2
    ATTR_TABLE:
      RENAME_SET_VALUE DestinationName > SumDestinationName (real64)
      RENAME_SET_VALUE Total_Distance > SumTotal_Distance (real64)
      REMOVE OBJECTID (int32)
      REMOVE col0 (real64)
      REMOVE OriginName (varchar(12))
      REMOVE OriginOID (real64)
      REMOVE DestinationID (real64)
      REMOVE DestinationOID (real64)
      REMOVE DestinationRank (real64)
      REMOVE Total_Time (real64)
      REMOVE pointid (int32)
      REMOVE OriginID (int32)
      REMOVE ForestedYN (int16)
      REMOVE ProcessingGroup (int16)
      REMOVE CK (varchar(16777216))
      REMOVE ILS_MILL_ID (varchar(16777216))
      REMOVE FORISK_MILL_ID (varchar(16777216))
      REMOVE MILL_CAPACITY_ID (varchar(16777216))
      REMOVE ANNUAL_PRODUCTION_CAPACITY_FORISK (number(7,1))
      REMOVE ANNUAL_PRODUCTION_CAPACITY_MI (number(38,2))
      REMOVE CAPITALID_ID (varchar(16777216))
      REMOVE DATE_ID (date)
      REMOVE END_USE_ID_FORISK (number(18,0))
      REMOVE HOUSEHOLD_SANITARY_FORISK (number(3,2))
      REMOVE HOUSEHOLD_SANITARY_MI (number(38,2))
      REMOVE MARKET_PULP_FORISK (number(5,4))
      REMOVE MARKET_PULP_MI (number(38,2))
      REMOVE MICROMARKET_ID (varchar(16777216))
      REMOVE MILL_OWNER_ID_FORISK (number(18,0))
      REMOVE MILL_STATUS_ID_MI (number(18,0))
      REMOVE MILL_STATUS_ID_FORISK (number(18,0))
      REMOVE NEWSPRINT_FORISK (number(5,4))
      REMOVE NEWSPRINT_MI (number(38,2))
      REMOVE OPERATING_RATE_MI (number(38,0))
      REMOVE PACKAGING_FORISK (number(4,3))
      REMOVE PACKAGING_MI (number(38,2))
      REMOVE PRINT_WRITING_FORISK (number(3,2))
      REMOVE PRINT_WRITING_MI (number(38,2))
      REMOVE PRODUCT_GROUP_ID (number(18,0))
      REMOVE RECYCLED_FORISK (number(3,2))
      REMOVE SORTS_GROUP_ID (number(18,0))
      REMOVE SPECIALTY_DISSOLVING_PULP_FORISK (number(3,2))
      REMOVE SPECIALTY_DISSOLVING_PULP_MI (number(38,2))
      REMOVE SPECIES_GROUP_ID (number(18,0))
      REMOVE SPECIES_ID_FORISK (number(18,0))
      REMOVE TL_ID (number(18,0))
      REMOVE VIABILITYID_ID (varchar(16777216))
      REMOVE WOOD_DEMAND_AT_CAPACITY_TONS_FORISK (number(9,0))
      REMOVE WOOD_DEMAND_AT_CAPACITY_TONS_MI (number(38,0))
      REMOVE SNOWFLAKE_LAST_UPDATED_DATE (datetime)
      REMOVE ILS_MILLS_ID (varchar(16777216))
      REMOVE CITY2 (varchar(16777216))
      REMOVE ILS_OWNER (varchar(16777216))
      REMOVE MILL_NAME (varchar(16777216))
      REMOVE PRIMARY_MILL_TYPE (varchar(16777216))
      REMOVE STATE_PROVINCE (varchar(16777216))
      REMOVE TL_AREA2 (varchar(16777216))
    USER_EXPOSED_ATTRIBUTES = DestinationName,Total_Distance,OBJECTID,col0,OriginName,OriginOID,DestinationID,DestinationOID,DestinationRank,Total_Time,pointid,OriginID,ForestedYN,ProcessingGroup,CK,ILS_MILL_ID,FORISK_MILL_ID,MILL_CAPACITY_ID,ANNUAL_PRODUCTION_CAPACITY_FORISK,ANNUAL_PRODUCTION_CAPACITY_MI,CAPITALID_ID,DATE_ID,END_USE_ID_FORISK,HOUSEHOLD_SANITARY_FORISK,HOUSEHOLD_SANITARY_MI,MARKET_PULP_FORISK,MARKET_PULP_MI,MICROMARKET_ID,MILL_OWNER_ID_FORISK,MILL_STATUS_ID_MI,MILL_STATUS_ID_FORISK,NEWSPRINT_FORISK,NEWSPRINT_MI,OPERATING_RATE_MI,PACKAGING_FORISK,PACKAGING_MI,PRINT_WRITING_FORISK,PRINT_WRITING_MI,PRODUCT_GROUP_ID,RECYCLED_FORISK,SORTS_GROUP_ID,SPECIALTY_DISSOLVING_PULP_FORISK,SPECIALTY_DISSOLVING_PULP_MI,SPECIES_GROUP_ID,SPECIES_ID_FORISK,TL_ID,VIABILITYID_ID,WOOD_DEMAND_AT_CAPACITY_TONS_FORISK,WOOD_DEMAND_AT_CAPACITY_TONS_MI,SNOWFLAKE_LAST_UPDATED_DATE,ILS_MILLS_ID,CITY2,ILS_OWNER,MILL_ID,MILL_NAME,PRIMARY_MILL_TYPE,STATE_PROVINCE,TL_AREA2,TL_REGION2
    -> FeatureJoiner_4 [RIGHT]
AvgTotalDistance: Aggregator
    ACCUM_ATTRS_NAME = Use Attributes From One Feature
    AGGREGATE_TYPE = Homogeneous Collection (If Possible)
    AV = Total_Distance
    GROUP_BY = DestinationName
    MODE = Geometry - Assemble One Level
    SEP = ,
    AGGREGATE -> AttributeManager
Note: Removed Total Time to avoid confusion
AttributeManager
    ATTR_TABLE:
      RENAME_SET_VALUE DestinationName > AvgTotalDestinationName (real64)
      RENAME_SET_VALUE Total_Distance > AvgTotal_Distance (real64)
      REMOVE Total_Time (real64)
    USER_EXPOSED_ATTRIBUTES = DestinationName,Total_Distance,OBJECTID,col0,OriginName,OriginOID,DestinationID,DestinationOID,DestinationRank,Total_Time,pointid,OriginID,ForestedYN,ProcessingGroup,CK,ILS_MILL_ID,FORISK_MILL_ID,MILL_CAPACITY_ID,ANNUAL_PRODUCTION_CAPACITY_FORISK,ANNUAL_PRODUCTION_CAPACITY_MI,CAPITALID_ID,DATE_ID,END_USE_ID_FORISK,HOUSEHOLD_SANITARY_FORISK,HOUSEHOLD_SANITARY_MI,MARKET_PULP_FORISK,MARKET_PULP_MI,MICROMARKET_ID,MILL_OWNER_ID_FORISK,MILL_STATUS_ID_MI,MILL_STATUS_ID_FORISK,NEWSPRINT_FORISK,NEWSPRINT_MI,OPERATING_RATE_MI,PACKAGING_FORISK,PACKAGING_MI,PRINT_WRITING_FORISK,PRINT_WRITING_MI,PRODUCT_GROUP_ID,RECYCLED_FORISK,SORTS_GROUP_ID,SPECIALTY_DISSOLVING_PULP_FORISK,SPECIALTY_DISSOLVING_PULP_MI,SPECIES_GROUP_ID,SPECIES_ID_FORISK,TL_ID,VIABILITYID_ID,WOOD_DEMAND_AT_CAPACITY_TONS_FORISK,WOOD_DEMAND_AT_CAPACITY_TONS_MI,SNOWFLAKE_LAST_UPDATED_DATE,ILS_MILLS_ID,CITY2,ILS_OWNER,MILL_ID,MILL_NAME,PRIMARY_MILL_TYPE,STATE_PROVINCE,TL_AREA2,TL_REGION2
    -> FeatureJoiner_4 [LEFT]
FeatureJoiner_4
    ATTR_CONFLICT_RES = Prefer Left
    GEOMETRY_HANDLING = Prefer Left
    JOIN_KEYS = MILL_ID MILL_ID AUTO
    JOIN_MODE = Inner
    JOINED -> FeatureJoiner_5 [LEFT]
FeatureJoiner_5
    ATTR_CONFLICT_RES = Prefer Left
    GEOMETRY_HANDLING = Prefer Left
    JOIN_KEYS = MILL_ID MILL_ID AUTO
    JOIN_MODE = Inner
    JOINED -> FeatureJoiner_6 [LEFT]
FeatureJoiner_6
    ATTR_CONFLICT_RES = Prefer Left
    GEOMETRY_HANDLING = Prefer Left
    JOIN_KEYS = MILL_ID MILL_ID AUTO
    JOIN_MODE = Inner
    JOINED -> FeatureJoiner [RIGHT]
Note: This data created by ILS_Mills_TPRWD Repository
Note: Need to decide if it makes sense to combine both workbenches
ILS_Mills_TPRWD (reader GEODATABASE_SDE_1)
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50), CK char(1073741822), CHIP_PRODUCTION_RATE float, CHIP_PRODUCTION double, FORISK_MILL_ID char(1073741822), ILS_MILL_ID char(1073741822), MILL_CAPACITY_ID char(1073741822), MILL_STATUS_ID_MI char(20), MILL_STATUS_ID_FORISK char(20), MILL_TYPE char(60), PELLET_ADJUSTMENT float, PINE_ROUNDWOOD_DEMAND double, PINE_ROUNDWOOD_DEMAND_ADJUSTMEN double, SPECIES_MULTIPLIER float, OPERATING_RATE double, WOOD_DEMAND_AT_CAPACITY double, WOOD_DEMAND_AT_CAPACITY_ADJUSTE double, ILS_MILLS_ID char(1073741822), CITY2 char(1073741822),
      ILS_OWNER char(1073741822), MILL_ID double, MILL_NAME char(1073741822), PRIMARY_MILL_TYPE char(1073741822), STATE_PROVINCE char(1073741822), TL_AREA2 char(1073741822), TL_REGION2 char(1073741822)
    -> FeatureJoiner [LEFT]
FeatureJoiner
    ATTR_CONFLICT_RES = Prefer Left
    GEOMETRY_HANDLING = Prefer Left
    JOIN_KEYS = MILL_ID SumDestinationName AUTO
    JOIN_MODE = Inner
    JOINED -> FeatureWriter [Joined]
Note: Tmp Location
FeatureWriter
    DATASET = TLDEVDBSFRS01_FIRST_FIRSTDW_Editor_V2
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor_V2
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Did_Write_Succeed
Did_Write_Succeed: Tester
    BOOL_OP = OR
    TEST_CLAUSE = TEST @Value(_total_features_written) > 0
    TEST_MODE = TEST
    PASSED -> FeatureReader [INITIATOR]
    FAILED -> Exit_Code_Check_2
Note: Re-Read Temp Loc
FeatureReader
    ATTRIBUTES = FIRST.ILS_Mills_TPRWD_Tmp,"OBJECTID,Source,MillID,MillName,ParentCompany,City,State,PrimaryMillType,SubMillType,Status,TL_Region,TL_Area,MicroMarketName,MicroMarketID,Latitude,Longitude,ModifiedOn,Address1,Address2,Address3,Country,ZipCode,DestinationID,LIMSName,MapLabel,ForiskID,ForiskName,ForiskStatus,Region,Capacity,Units,Species,EndUse,Demand_tons,RecycledPct,Newsprint,Printing_Writing,Household_Sanitary,Packaging,Specialty_DissolvingPulp,MarketPulp,Certification,CK,CHIP_PRODUCTION_RATE,CHIP_PRODUCTION,FORISK_MILL_ID,ILS_MILL_ID,MILL_CAPACITY_ID,MILL_STATUS_ID_MI,MILL_STATUS_ID_FORISK,MILL_TYPE,PELLET_ADJUSTMENT,PINE_ROUNDWOOD_DEMAND,PINE_ROUNDWOOD_DEMAND_ADJUSTMEN,SPECIES_MULTIPLIER,OPERATING_RATE,WOOD_DEMAND_AT_CAPACITY,WOOD_DEMAND_AT_CAPACITY_ADJUSTE,ILS_MILLS_ID,CITY2,ILS_OWNER,MILL_ID,MILL_NAME,PRIMARY_MILL_TYPE,STATE_PROVINCE,TL_AREA2,TL_REGION2,AvgTotalDestinationName,AvgTotal_Distance,col0,OriginName,OriginOID,DestinationOID,DestinationRank,pointid,OriginID,ForestedYN,ProcessingGroup,ANNUAL_PRODUCTION_CAPACITY_FORI,ANNUAL_PRODUCTION_CAPACITY_MI,CAPITALID_ID,DATE_ID,END_USE_ID_FORISK,HOUSEHOLD_SANITARY_FORISK,HOUSEHOLD_SANITARY_MI,MARKET_PULP_FORISK,MARKET_PULP_MI,MICROMARKET_ID,MILL_OWNER_ID_FORISK,NEWSPRINT_FORISK,NEWSPRINT_MI,OPERATING_RATE_MI,PACKAGING_FORISK,PACKAGING_MI,PRINT_WRITING_FORISK,PRINT_WRITING_MI,PRODUCT_GROUP_ID,RECYCLED_FORISK,SORTS_GROUP_ID,SPECIALTY_DISSOLVING_PULP_FORIS,SPECIALTY_DISSOLVING_PULP_MI,SPECIES_GROUP_ID,SPECIES_ID_FORISK,TL_ID,VIABILITYID_ID,WOOD_DEMAND_AT_CAPACITY_TONS_FO,WOOD_DEMAND_AT_CAPACITY_TONS_MI,SNOWFLAKE_LAST_UPDATED_DATE,SumDestinationName,SumTotal_Distance,AvgDestinationName,AvgTotal_Time,SumTimeDestinationName,SumTotal_Time"
    ATTR_ACCUM_MODE = Only Use Result
    COMBINE_GEOM = Use Result
    DATASET = TLDEVDBSFRS01_FIRST_FIRSTDW_Editor_V2
    FEATURETYPES = FIRST.ILS_Mills_TPRWD_Tmp
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CREATE_FEATURE_TABLES_FROM_DATA = Yes
    GEODATABASE_SDE_DISABLE_FEATURE_DATASET_ATTRIBUTE = Yes
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_NAMED_CONNECTION = TLDEVDBSFRS01_FIRST_FIRSTDW_Editor_V2
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_FEATURE_DATASET = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TABLELIST = FIRST.ODMatrixFake
    GEODATABASE_SDE_TRANSLATE_SPATIAL_DATA_ONLY = no
    GEODATABASE_SDE_USE_SEARCH_ENVELOPE = NO
    GEOMETRY_TYPES = FIRST.ILS_Mills_TPRWD_Tmp,""",fme_point"""
    INTERACT = NONE
    ORDER_RESULTS = No
    OUTPUT_ADD_SCHEMA_ATTRIBUTES = NO
    OUTPUT_FEATURES_DISPLAY = Schema and Data Features
    FIRST.ILS_Mills_TPRWD_Tmp -> SumTimeBufferer
    FIRST.ILS_Mills_TPRWD_Tmp -> SumDistanceBufferer
    FIRST.ILS_Mills_TPRWD_Tmp -> AvgDistanceBufferer
    FIRST.ILS_Mills_TPRWD_Tmp -> AvgTimeBufferer
Note: Buffer units meters, and buffer distance is multiplied by 1/2
SumTimeBufferer: Bufferer
    ANGLE = 22.5
    CAP_STYLE = Arc
    CORNER_STYLE = Arc
    MODE = AREA
    OFFSET = @Value(SumTotal_Time) * 0.5
    OFFSET_UNITS = METERS
    PRECISION = APPROX
    BUFFERED -> SumTimeFeatureWriter [Buffered]
    <REJECTED> -> Counter_Check_for_Rejects
SumTimeFeatureWriter: FeatureWriter
    DATASET = TLDEVDBSFRS01_FIRST_FIRSTDW_Editor_V2
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor_V2
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Did_All_Writes_Succeed
Did_All_Writes_Succeed: Tester
    BOOL_OP = OR
    TEST_CLAUSE = TEST @Value(_total_features_written) > 0
    TEST_MODE = TEST
    PASSED -> FeatureHolder
    FAILED -> Exit_Code_Check
Exit_Code_Check: Terminator
    MESSAGE = Creating buffers failed
SumDistanceBufferer: Bufferer
    ANGLE = 22.5
    CAP_STYLE = Arc
    CORNER_STYLE = Arc
    MODE = AREA
    OFFSET = @Value(SumTotal_Distance) * 0.5
    OFFSET_UNITS = METERS
    PRECISION = APPROX
    BUFFERED -> SumDistFeatureWriter [Buffered]
    <REJECTED> -> Counter_Check_for_Rejects
SumDistFeatureWriter: FeatureWriter
    DATASET = TLDEVDBSFRS01_FIRST_FIRSTDW_Editor_V2
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor_V2
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Did_All_Writes_Succeed_2
Did_All_Writes_Succeed_2: Tester
    BOOL_OP = OR
    TEST_CLAUSE = TEST @Value(_total_features_written) > 0
    TEST_MODE = TEST
    PASSED -> FeatureHolder
    FAILED -> Exit_Code_Check_4
Exit_Code_Check_4: Terminator
    MESSAGE = Creating buffers failed
AvgDistanceBufferer: Bufferer
    ANGLE = 22.5
    CAP_STYLE = Arc
    CORNER_STYLE = Arc
    MODE = AREA
    OFFSET = @Value(AvgTotal_Distance) * 0.5
    OFFSET_UNITS = METERS
    PRECISION = APPROX
    BUFFERED -> AvgDistFeatureWriter [Buffered]
    <REJECTED> -> Counter_Check_for_Rejects
AvgDistFeatureWriter: FeatureWriter
    DATASET = TLDEVDBSFRS01_FIRST_FIRSTDW_Editor_V2
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor_V2
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Did_All_Writes_Succeed_3
Did_All_Writes_Succeed_3: Tester
    BOOL_OP = OR
    TEST_CLAUSE = TEST @Value(_total_features_written) > 0
    TEST_MODE = TEST
    PASSED -> FeatureHolder
    FAILED -> Exit_Code_Check_5
Exit_Code_Check_5: Terminator
    MESSAGE = Creating buffers failed
AvgTimeBufferer: Bufferer
    ANGLE = 22.5
    CAP_STYLE = Arc
    CORNER_STYLE = Arc
    MODE = AREA
    OFFSET = @Value(AvgTotal_Time) * 0.5
    OFFSET_UNITS = METERS
    PRECISION = APPROX
    BUFFERED -> AvgTimeFeatureWriter [Buffered]
    <REJECTED> -> Counter_Check_for_Rejects
AvgTimeFeatureWriter: FeatureWriter
    DATASET = TLDEVDBSFRS01_FIRST_FIRSTDW_Editor_V2
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor_V2
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Did_All_Writes_Succeed_4
Did_All_Writes_Succeed_4: Tester
    BOOL_OP = OR
    TEST_CLAUSE = TEST @Value(_total_features_written) > 0
    TEST_MODE = TEST
    PASSED -> FeatureHolder
    FAILED -> Exit_Code_Check_6
FeatureHolder
    -> Sampler_2
Sampler_2
    RATE = 1
    SAMPLE_MODE = No
    SAMPLE_TYPE_LONG = First N Features
    SAMPLED -> Tester_2
Tester_2
    BOOL_OP = OR
    TEST_CLAUSE = TEST @Value(_total_features_written) > 0
    TEST_MODE = TEST
    PASSED -> Create_Rasters
    FAILED -> Exit_Code_Check_7
Note: Python Script Requires Spatial License for Kernel Raster Layers
Note: Kernel Density fails with one point
Note: 05/02/24 Script uses fake layers for testing. Will need modification when other parts are working.
Note: TODO make env a variable based on machine
Create_Rasters: SystemCaller
    ATTR = raster_exit_code
    CMD = D:\ArcGIS\Pro\bin\Python\envs\arcgispro-py3\python.exe "\\TLTSTAPGISFME01\FME_Share\LeonardL1\Python\ChangeDetector\VectorToRaster.py"
    -> ESRI_Check_Exit_Code
ESRI_Check_Exit_Code: Tester
    BOOL_OP = OR
    TEST_CLAUSE = TEST @Value(raster_exit_code) = 0
    TEST_MODE = TEST
    FAILED -> ESRI_Exit_Code_Check
ESRI_Exit_Code_Check: Terminator
    MESSAGE = Creating raster layers and KernelDensity failed.
Exit_Code_Check_7: Terminator
    MESSAGE = Creating buffers failed
Exit_Code_Check_6: Terminator
    MESSAGE = Creating buffers failed
Note: For now rejects will cancel this workspace. Will need to re-evaluate after bigger sample size
Counter_Check_for_Rejects
    CNT_ATTR = _count
    DOMAIN = counter
    SCOPE = Global
    START = 0
    -> Tester
Tester
    BOOL_OP = OR
    TEST_CLAUSE = TEST @Value(_count) > 0
    TEST_MODE = TEST
    FAILED -> Exit_Code_Check_3
Exit_Code_Check_3: Terminator
    MESSAGE = Rejects found in buffers. For now exiting to debug why.
Exit_Code_Check_2: Terminator
    MESSAGE = Creating ILS_Mills_TPRWD_Tmp failed
Note: For dev env
Create_Rasters_2: SystemCaller [off]
    ATTR = raster_exit_code
    CMD = E:\Projects\PythonProEnv\python.exe "\\TLTSTAPGISFME01\FME_Share\LeonardL1\Python\ChangeDetector\VectorToRaster.py"

Bookmark: SnowFlake
FACT_MI_MILL (reader SNOWFLAKE_NONSPATIAL_2) [off]
    attributes: CK varchar(16777216), ILS_MILL_ID varchar(16777216), FORISK_MILL_ID varchar(16777216), MILL_CAPACITY_ID varchar(16777216), ANNUAL_PRODUCTION_CAPACITY_FORISK number(7,1), ANNUAL_PRODUCTION_CAPACITY_MI number(38,2), CAPITALID_ID varchar(16777216), DATE_ID date, END_USE_ID_FORISK number(18,0), HOUSEHOLD_SANITARY_FORISK number(3,2), HOUSEHOLD_SANITARY_MI number(38,2), MARKET_PULP_FORISK number(5,4), MARKET_PULP_MI number(38,2), MICROMARKET_ID varchar(16777216), MILL_OWNER_ID_FORISK number(18,0), MILL_STATUS_ID_MI number(18,0), MILL_STATUS_ID_FORISK number(18,0), NEWSPRINT_FORISK number(5,4), NEWSPRINT_MI number(38,2), OPERATING_RATE_MI number(38,0), PACKAGING_FORISK number(4,3), PACKAGING_MI number(38,2), PRINT_WRITING_FORISK number(3,2), PRINT_WRITING_MI number(38,2), PRODUCT_GROUP_ID number(18,0), RECYCLED_FORISK number(3,2), SORTS_GROUP_ID number(18,0), SPECIALTY_DISSOLVING_PULP_FORISK number(3,2), SPECIALTY_DISSOLVING_PULP_MI number(38,2), SPECIES_GROUP_ID number(18,0),
      SPECIES_ID_FORISK number(18,0), TL_ID number(18,0), VIABILITYID_ID varchar(16777216), WOOD_DEMAND_AT_CAPACITY_TONS_FORISK number(9,0), WOOD_DEMAND_AT_CAPACITY_TONS_MI number(38,0), SNOWFLAKE_LAST_UPDATED_DATE timestamp_ntz
    -> FeatureJoiner_3 [LEFT]
DIM_MI_MILL (reader SNOWFLAKE_NONSPATIAL_2) [off]
    attributes: ILS_MILLS_ID varchar(16777216), CITY varchar(16777216), ILS_OWNER varchar(16777216), MILL_ID number(38,0), MILL_NAME varchar(16777216), PRIMARY_MILL_TYPE varchar(16777216), STATE_PROVINCE varchar(16777216), TL_AREA varchar(16777216), TL_REGION varchar(16777216)
    -> FeatureJoiner_3 [RIGHT]

Bookmark: SnowFlake QA
DIM_MI_MILL (reader SNOWFLAKE_NONSPATIAL_1)
    attributes: ILS_MILLS_ID varchar(16777216), CITY varchar(16777216), ILS_OWNER varchar(16777216), MILL_ID number(38,0), MILL_NAME varchar(16777216), PRIMARY_MILL_TYPE varchar(16777216), STATE_PROVINCE varchar(16777216), TL_AREA varchar(16777216), TL_REGION varchar(16777216)
    -> FeatureJoiner_3 [RIGHT]
FACT_MI_MILL (reader SNOWFLAKE_NONSPATIAL_1)
    attributes: CK varchar(16777216), ILS_MILL_ID varchar(16777216), FORISK_MILL_ID varchar(16777216), MILL_CAPACITY_ID varchar(16777216), ANNUAL_PRODUCTION_CAPACITY_FORISK number(7,1), ANNUAL_PRODUCTION_CAPACITY_MI number(38,2), CAPITALID_ID varchar(16777216), DATE_ID date, END_USE_ID_FORISK number(18,0), HOUSEHOLD_SANITARY_FORISK number(3,2), HOUSEHOLD_SANITARY_MI number(38,2), MARKET_PULP_FORISK number(5,4), MARKET_PULP_MI number(38,2), MICROMARKET_ID varchar(16777216), MILL_OWNER_ID_FORISK number(18,0), MILL_STATUS_ID_MI number(18,0), MILL_STATUS_ID_FORISK number(18,0), NEWSPRINT_FORISK number(5,4), NEWSPRINT_MI number(38,2), OPERATING_RATE_MI number(38,0), PACKAGING_FORISK number(4,3), PACKAGING_MI number(38,2), PRINT_WRITING_FORISK number(3,2), PRINT_WRITING_MI number(38,2), PRODUCT_GROUP_ID number(18,0), RECYCLED_FORISK number(3,2), SORTS_GROUP_ID number(18,0), SPECIALTY_DISSOLVING_PULP_FORISK number(3,2), SPECIALTY_DISSOLVING_PULP_MI number(38,2), SPECIES_GROUP_ID number(18,0),
      SPECIES_ID_FORISK number(18,0), TL_ID number(18,0), VIABILITYID_ID varchar(16777216), WOOD_DEMAND_AT_CAPACITY_TONS_FORISK number(9,0), WOOD_DEMAND_AT_CAPACITY_TONS_MI number(38,0), SNOWFLAKE_LAST_UPDATED_DATE timestamp_ntz
    -> FeatureJoiner_3 [LEFT]
