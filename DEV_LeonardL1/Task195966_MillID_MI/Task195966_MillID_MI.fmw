FME workspace Task195966_MillID_MI.fmw

Parameters:
- SourceDataset_GEODATABASE_SDE = TLDEVDBSFRS01_FIRST_FIRSTDW_Viewer.sde   # ArcSDE Geodatabase Connection
- DestDataset_GEODATABASE_SDE = TLDEVDBSFRS01_FIRST_FIRSTDW_Editor.sde   # ArcSDE Geodatabase Connection
- SourceDataset_SNOWFLAKE_NONSPATIAL_3 = DEV_CDO_FME_FIRST_SRVACCT_PL_MI   # Connection
- DestDataset_GEODATABASE_FILE = E:\Projects\FIRST\FIRST Data Warehouse\MillsForChangeDetection.gdb   # File Geodatabase
- SourceDataset_GEODATABASE_FILE = E:\Projects\FIRST\FIRST Data Warehouse\MillsForChangeDetection.gdb   # File Geodatabase
- SourceDataset_GEODATABASE_SDE_2 = TLDEVDBSFRS01_FIRST_FIRSTDW_Viewer.sde   # ArcSDE Geodatabase Connection
- DestDataset_GEODATABASE_SDE_3 = TLDEVDBSFRS01_FIRST_FIRSTDW_Editor.sde   # ArcSDE Geodatabase Connection
- SourceDataset_GEODATABASE_SDE_4 = TLDEVDBSFRS01_FIRST_FIRSTDW_Viewer.sde   # ArcSDE Geodatabase Connection

Readers:
- GEODATABASE_SDE_1: GEODATABASE_SDE from $(SourceDataset_GEODATABASE_SDE)
- SNOWFLAKE_NONSPATIAL_2: SNOWFLAKE_NONSPATIAL from $(SourceDataset_SNOWFLAKE_NONSPATIAL_3)
- GEODATABASE_FILE_2: GEODATABASE_FILE from $(SourceDataset_GEODATABASE_FILE)
- GEODATABASE_SDE_3: GEODATABASE_SDE from $(SourceDataset_GEODATABASE_SDE_2)
- GEODATABASE_SDE_5: GEODATABASE_SDE from $(SourceDataset_GEODATABASE_SDE_4)

Writers:
- GEODATABASE_SDE_2: GEODATABASE_SDE to $(DestDataset_GEODATABASE_SDE)
- GEODATABASE_FILE_1: GEODATABASE_FILE to $(DestDataset_GEODATABASE_FILE)
- GEODATABASE_SDE_4: GEODATABASE_SDE to $(DestDataset_GEODATABASE_SDE_3)

Note: TODO TEST once meaningful data uploaded
MillsRing (reader GEODATABASE_SDE_1)
    attributes: OBJECTID integer, name char(40), frombreak double, tobreak double, facilityoid double, facilityid double, name_1 char(20), source char(508), millid char(508), millname char(508), parentcompany char(508), city char(508), state char(508), primarymilltype char(508), submilltype char(508), tl_region char(508), tl_area char(508), micromarketname char(508), micromarketid char(508), latitude char(508), longitude char(508), modifiedon date, address1 char(508), address2 char(508), address3 char(508), country char(508), zipcode char(508), destinationid char(508), limsname char(508), maplabel char(508),
      foriskid char(508), foriskname char(508), foriskstatus char(508), region char(508), capacity char(508), units char(508), species char(508), enduse char(508), demand_tons char(508), recycledpct char(508), newsprint char(508), printing_writing char(508), household_sanitary char(508), packaging char(508), specialty_dissolvingpulp char(508), marketpulp char(508), certification char(508), breaks char(508), additionaltime double, additionaldistance double, SHAPE.STArea() double, SHAPE.STLength() double
    -> AttributeManager
AttributeManager
    -> MITest (writer GEODATABASE_FILE_1)
    -> FeatureJoiner [LEFT]
Note: Changed mill id to 19678
MITest (writer GEODATABASE_FILE_1) [off]
    attributes: OBJECTID integer, name char(40), frombreak double, tobreak double, facilityoid double, facilityid double, name_1 char(20), source char(508), millid double(38,0), millname char(508), parentcompany char(508), city char(508), state char(508), primarymilltype char(508), submilltype char(508), tl_region char(508), tl_area char(508), micromarketname char(508), micromarketid char(508), latitude char(508), longitude char(508), modifiedon date, address1 char(508), address2 char(508), address3 char(508), country char(508), zipcode char(508), destinationid char(508), limsname char(508), maplabel char(508),
      foriskid char(508), foriskname char(508), foriskstatus char(508), region char(508), capacity char(508), units char(508), species char(508), enduse char(508), demand_tons char(508), recycledpct char(508), newsprint char(508), printing_writing char(508), household_sanitary char(508), packaging char(508), specialty_dissolvingpulp char(508), marketpulp char(508), certification char(508), breaks char(508), additionaltime double, additionaldistance double, SHAPE_STArea__ double, SHAPE_STLength__ double
Note: TODO TEST once meaningful data uploaded
Note: TODO TEST once meaningful data uploaded
MillsDrive (reader GEODATABASE_SDE_3)
    attributes: OBJECTID integer, country char(8), specialty_dissolvingpulp char(8), source char(8), millname char(8), parentcompany char(8), state char(8), limsname char(8), additionaldistance double, longitude char(8), marketpulp char(8), tl_region char(8), foriskid char(8), micromarketid char(8), certification char(8), zipcode char(8), modifiedon date, tobreak double, demand_tons char(8), name char(38), analysisarea double, region char(8), name_1 char(20), primarymilltype char(8), maplabel char(8), city char(8), latitude char(8), units char(8), millid char(8), capacity char(8),
      household_sanitary char(8), submilltype char(8), recycledpct char(8), enduse char(8), newsprint char(8), foriskname char(8), address3 char(8), breaks char(8), address2 char(8), address1 char(8), facilityoid integer, packaging char(8), destinationid char(8), frombreak double, foriskstatus char(8), tl_area char(8), micromarketname char(8), additionaltime double, species char(8), printing_writing char(8), SHAPE.STArea() double, SHAPE.STLength() double
    -> AttributeManager_3
AttributeManager_3
    -> FeatureJoiner_2 [LEFT]
ODMatrix (reader GEODATABASE_SDE_5)
    attributes: OBJECTID integer, col0 double, OriginName char(12), OriginOID double, DestinationOID double, Total_Distance double, Total_Time double, DestinationID double, DestinationName double, DestinationRank double
    -> AttributeManager_5
AttributeManager_5
    -> FeatureJoiner_3 [LEFT]
DIM_MI_MILL (reader SNOWFLAKE_NONSPATIAL_2)
    attributes: ILS_MILLS_ID varchar(16777216), CITY varchar(16777216), ILS_OWNER varchar(16777216), MILL_ID number(38,0), MILL_NAME varchar(16777216), PRIMARY_MILL_TYPE varchar(16777216), STATE_PROVINCE varchar(16777216), TL_AREA varchar(16777216), TL_REGION varchar(16777216)
    -> FeatureJoiner [RIGHT]
    -> FeatureJoiner_2 [RIGHT]
    -> FeatureJoiner_3 [RIGHT]
FeatureJoiner_2
    ATTR_CONFLICT_RES = Prefer Left
    GEOMETRY_HANDLING = Prefer Left
    JOIN_KEYS = millid MILL_ID AUTO
    JOIN_MODE = Inner
    JOINED -> AttributeManager_4
AttributeManager_4
    ATTR_TABLE:
      RENAME_SET_VALUE CITY > CITY2 (varchar(16777216))
      RENAME_SET_VALUE MILL_ID (number(38,0))
      RENAME_SET_VALUE TL_AREA > TL_AREA2 (varchar(16777216))
      RENAME_SET_VALUE TL_REGION > TL_REGION2 (varchar(16777216))
    USER_EXPOSED_ATTRIBUTES = OBJECTID,name,frombreak,tobreak,facilityoid,name_1,source,millid,millname,parentcompany,city,state,primarymilltype,submilltype,tl_region,tl_area,micromarketname,micromarketid,latitude,longitude,modifiedon,address1,address2,address3,country,zipcode,destinationid,limsname,maplabel,foriskid,foriskname,foriskstatus,region,capacity,units,species,enduse,demand_tons,recycledpct,newsprint,printing_writing,household_sanitary,packaging,specialty_dissolvingpulp,marketpulp,certification,breaks,additionaltime,additionaldistance,SHAPE.STArea(),SHAPE.STLength(),analysisarea,ILS_MILLS_ID,CITY,ILS_OWNER,MILL_ID,MILL_NAME,PRIMARY_MILL_TYPE,STATE_PROVINCE,TL_AREA,TL_REGION
    -> MI_MillsDrive (writer GEODATABASE_SDE_4)
MI_MillsDrive (writer GEODATABASE_SDE_4)
    attributes: OBJECTID integer, name char(38), frombreak double, tobreak double, facilityoid integer, name_1 char(20), source char(8), millid double(38,0), millname char(8), parentcompany char(8), city char(8), state char(8), primarymilltype char(8), submilltype char(8), tl_region char(8), tl_area char(8), micromarketname char(8), micromarketid char(8), latitude char(8), longitude char(8), modifiedon date, address1 char(8), address2 char(8), address3 char(8), country char(8), zipcode char(8), destinationid char(8), limsname char(8), maplabel char(8), foriskid char(8),
      foriskname char(8), foriskstatus char(8), region char(8), capacity char(8), units char(8), species char(8), enduse char(8), demand_tons char(8), recycledpct char(8), newsprint char(8), printing_writing char(8), household_sanitary char(8), packaging char(8), specialty_dissolvingpulp char(8), marketpulp char(8), certification char(8), breaks char(8), additionaltime double, additionaldistance double, SHAPE_STArea__ double, SHAPE_STLength__ double, analysisarea double, ILS_MILLS_ID char(16777216), CITY2 char(16777216), ILS_OWNER char(16777216), MILL_ID double(38,0), MILL_NAME char(16777216), PRIMARY_MILL_TYPE char(16777216), STATE_PROVINCE char(16777216), TL_AREA2 char(16777216),
      TL_REGION2 char(16777216)
FeatureJoiner_3
    ATTR_CONFLICT_RES = Prefer Left
    GEOMETRY_HANDLING = Prefer Left
    JOIN_KEYS = DestinationName MILL_ID AUTO
    JOIN_MODE = Inner
    JOINED -> AttributeManager_6
AttributeManager_6
    ATTR_TABLE:
      RENAME_SET_VALUE CITY > CITY2 (varchar(16777216))
      RENAME_SET_VALUE MILL_ID (number(38,0))
      RENAME_SET_VALUE TL_AREA > TL_AREA2 (varchar(16777216))
      RENAME_SET_VALUE TL_REGION > TL_REGION2 (varchar(16777216))
    USER_EXPOSED_ATTRIBUTES = OBJECTID,name,frombreak,tobreak,facilityoid,name_1,source,millid,millname,parentcompany,city,state,primarymilltype,submilltype,tl_region,tl_area,micromarketname,micromarketid,latitude,longitude,modifiedon,address1,address2,address3,country,zipcode,destinationid,limsname,maplabel,foriskid,foriskname,foriskstatus,region,capacity,units,species,enduse,demand_tons,recycledpct,newsprint,printing_writing,household_sanitary,packaging,specialty_dissolvingpulp,marketpulp,certification,breaks,additionaltime,additionaldistance,SHAPE.STArea(),SHAPE.STLength(),analysisarea,ILS_MILLS_ID,CITY,ILS_OWNER,MILL_ID,MILL_NAME,PRIMARY_MILL_TYPE,STATE_PROVINCE,TL_AREA,TL_REGION
    -> MI_ODMatrix (writer GEODATABASE_SDE_4)
MI_ODMatrix (writer GEODATABASE_SDE_4)
    attributes: OBJECTID integer, name char(38), frombreak double, tobreak double, facilityoid integer, name_1 char(20), source char(8), millid double(38,0), millname char(8), parentcompany char(8), city char(8), state char(8), primarymilltype char(8), submilltype char(8), tl_region char(8), tl_area char(8), micromarketname char(8), micromarketid char(8), latitude char(8), longitude char(8), modifiedon date, address1 char(8), address2 char(8), address3 char(8), country char(8), zipcode char(8), destinationid char(8), limsname char(8), maplabel char(8), foriskid char(8),
      foriskname char(8), foriskstatus char(8), region char(8), capacity char(8), units char(8), species char(8), enduse char(8), demand_tons char(8), recycledpct char(8), newsprint char(8), printing_writing char(8), household_sanitary char(8), packaging char(8), specialty_dissolvingpulp char(8), marketpulp char(8), certification char(8), breaks char(8), additionaltime double, additionaldistance double, analysisarea double, ILS_MILLS_ID char(16777216), CITY2 char(16777216), ILS_OWNER char(16777216), MILL_ID double(38,0), MILL_NAME char(16777216), PRIMARY_MILL_TYPE char(16777216), STATE_PROVINCE char(16777216), TL_AREA2 char(16777216), TL_REGION2 char(16777216), col0 double,
      OriginName char(12), OriginOID double, DestinationOID double, Total_Distance double, Total_Time double, DestinationID double, DestinationName double, DestinationRank double
Note: Need to swap once better dataset available
MITest (reader GEODATABASE_FILE_2) [off]
    attributes: OBJECTID integer, name char(40), frombreak double, tobreak double, facilityoid double, facilityid double, name_1 char(20), source char(508), millid double, millname char(508), parentcompany char(508), city char(508), state char(508), primarymilltype char(508), submilltype char(508), tl_region char(508), tl_area char(508), micromarketname char(508), micromarketid char(508), latitude char(508), longitude char(508), modifiedon date, address1 char(508), address2 char(508), address3 char(508), country char(508), zipcode char(508), destinationid char(508), limsname char(508), maplabel char(508),
      foriskid char(508), foriskname char(508), foriskstatus char(508), region char(508), capacity char(508), units char(508), species char(508), enduse char(508), demand_tons char(508), recycledpct char(508), newsprint char(508), printing_writing char(508), household_sanitary char(508), packaging char(508), specialty_dissolvingpulp char(508), marketpulp char(508), certification char(508), breaks char(508), additionaltime double, additionaldistance double, SHAPE_Length double, SHAPE_Area double
    -> FeatureJoiner [LEFT]
FeatureJoiner
    ATTR_CONFLICT_RES = Prefer Left
    GEOMETRY_HANDLING = Prefer Left
    JOIN_KEYS = millid MILL_ID AUTO
    JOIN_MODE = Inner
    JOINED -> AttributeManager_2
AttributeManager_2
    ATTR_TABLE:
      RENAME_SET_VALUE CITY > CITY2 (varchar(16777216))
      RENAME_SET_VALUE PRIMARY_MILL_TYPE > PRIMARY_MILL_TYPE2 (varchar(16777216))
      RENAME_SET_VALUE STATE_PROVINCE > STATE_PROVINCE2 (varchar(16777216))
      RENAME_SET_VALUE TL_AREA > TL_AREA2 (varchar(16777216))
      RENAME_SET_VALUE TL_REGION > TL_REGION2 (varchar(16777216))
    -> MITestJoin (writer GEODATABASE_FILE_1)
    -> MI_MillsRing (writer GEODATABASE_SDE_4)
MITestJoin (writer GEODATABASE_FILE_1) [off]
    attributes: OBJECTID integer, name char(40), frombreak double, tobreak double, facilityoid double, facilityid double, name_1 char(20), source char(508), millid double, millname char(508), parentcompany char(508), city char(508), state char(508), primarymilltype char(508), submilltype char(508), tl_region char(508), tl_area char(508), micromarketname char(508), micromarketid char(508), latitude char(508), longitude char(508), modifiedon date, address1 char(508), address2 char(508), address3 char(508), country char(508), zipcode char(508), destinationid char(508), limsname char(508), maplabel char(508),
      foriskid char(508), foriskname char(508), foriskstatus char(508), region char(508), capacity char(508), units char(508), species char(508), enduse char(508), demand_tons char(508), recycledpct char(508), newsprint char(508), printing_writing char(508), household_sanitary char(508), packaging char(508), specialty_dissolvingpulp char(508), marketpulp char(508), certification char(508), breaks char(508), additionaltime double, additionaldistance double, SHAPE_Length double, SHAPE_Area double, ILS_MILLS_ID char(16777216), CITY2 char(16777216), ILS_OWNER char(16777216), MILL_ID double(38,0), MILL_NAME char(16777216), PRIMARY_MILL_TYPE2 char(16777216), STATE_PROVINCE2 char(16777216), TL_AREA2 char(16777216),
      TL_REGION2 char(16777216), SHAPE_STArea__ double, SHAPE_STLength__ double
MI_MillsRing (writer GEODATABASE_SDE_4)
    attributes: OBJECTID integer, name char(40), frombreak double, tobreak double, facilityoid double, facilityid double, name_1 char(20), source char(508), millid double, millname char(508), parentcompany char(508), city char(508), state char(508), primarymilltype char(508), submilltype char(508), tl_region char(508), tl_area char(508), micromarketname char(508), micromarketid char(508), latitude char(508), longitude char(508), modifiedon date, address1 char(508), address2 char(508), address3 char(508), country char(508), zipcode char(508), destinationid char(508), limsname char(508), maplabel char(508),
      foriskid char(508), foriskname char(508), foriskstatus char(508), region char(508), capacity char(508), units char(508), species char(508), enduse char(508), demand_tons char(508), recycledpct char(508), newsprint char(508), printing_writing char(508), household_sanitary char(508), packaging char(508), specialty_dissolvingpulp char(508), marketpulp char(508), certification char(508), breaks char(508), additionaltime double, additionaldistance double, SHAPE_Length double, SHAPE_Area double, ILS_MILLS_ID char(16777216), CITY2 char(16777216), ILS_OWNER char(16777216), MILL_ID double(38,0), MILL_NAME char(16777216), PRIMARY_MILL_TYPE2 char(16777216), STATE_PROVINCE2 char(16777216), TL_AREA2 char(16777216),
      TL_REGION2 char(16777216), SHAPE_STArea__ double, SHAPE_STLength__ double
