FME workspace ILS_Mills_TPRWD.fmw

Parameters:
- SourceDataset_GEODATABASE_SDE = FME-ILS-DEV-RO-V2   # ArcSDE Geodatabase Connection

Readers:
- GEODATABASE_SDE_1: GEODATABASE_SDE from $(SourceDataset_GEODATABASE_SDE)

Creator
    GEOMTYPE = Geometry Object
    NUM = 1
    CREATED -> FeatureReader [INITIATOR]
    CREATED -> FeatureReader_2 [INITIATOR]
Note: Uses a temporary SnowFlake location. These two tables will change once PR accepted.
FeatureReader [off]
    ATTRIBUTES = PL_MI.DIM_MI_MILL,"ILS_MILLS_ID,CITY,ILS_OWNER,MILL_ID,MILL_NAME,PRIMARY_MILL_TYPE,STATE_PROVINCE,TL_AREA,TL_REGION",PL_MI.PORTFOLIO_PL_MI_FACT_TOTAL_PINE_ROUNDWOOD_DEMAND,"CK,CHIP_PRODUCTION_RATE,CHIP_PRODUCTION,FORISK_MILL_ID,ILS_MILL_ID,MILL_CAPACITY_ID,MILL_STATUS_ID_MI,MILL_STATUS_ID_FORISK,MILL_TYPE,PELLET_ADJUSTMENT,PINE_ROUNDWOOD_DEMAND,PINE_ROUNDWOOD_DEMAND_ADJUSTMENT,SPECIES_MULTIPLIER,OPERATING_RATE,WOOD_DEMAND_AT_CAPACITY,WOOD_DEMAND_AT_CAPACITY_ADJUSTED"
    ATTR_ACCUM_MODE = Only Use Result
    COMBINE_GEOM = Use Result
    DATASET = DEV_snowflake_DEV-CDO-PORTFOLIO-MANAGEMENT-PL-MI-srvacct
    FEATURETYPES = PL_MI.PORTFOLIO_PL_MI_FACT_TOTAL_PINE_ROUNDWOOD_DEMAND PL_MI.DIM_MI_MILL
    FORMAT = SNOWFLAKE_NONSPATIAL
    GEOMETRY_TYPES = PL_MI.DIM_MI_MILL,""",fme_area,fme_collection,fme_line,fme_point""",PL_MI.PORTFOLIO_PL_MI_FACT_TOTAL_PINE_ROUNDWOOD_DEMAND,""",fme_area,fme_collection,fme_line,fme_point"""
    ORDER_RESULTS = No
    OUTPUT_ADD_SCHEMA_ATTRIBUTES = NO
    OUTPUT_FEATURES_DISPLAY = Schema and Data Features
    SNOWFLAKE_NONSPATIAL_COERCE_VARIANT_TO_JSON = No
    SNOWFLAKE_NONSPATIAL_CREATE_FEATURE_TABLES_FROM_DATA = Yes
    SNOWFLAKE_NONSPATIAL_NAMED_CONNECTION = DEV_snowflake_DEV-CDO-PORTFOLIO-MANAGEMENT-PL-MI-srvacct
    SNOWFLAKE_NONSPATIAL_QUERY_FEATURE_TYPES_FOR_MERGE_FILTERS = Yes
    SNOWFLAKE_NONSPATIAL_QUERY_TIMEOUT = 30
    PL_MI.PORTFOLIO_PL_MI_FACT_TOTAL_PINE_ROUNDWOOD_DEMAND -> FeatureMerger [REQUESTOR]
    PL_MI.DIM_MI_MILL -> FeatureMerger [SUPPLIER]
Note: QAQC
FeatureReader_2
    ATTRIBUTES = PL_MI.DIM_MI_MILL,"ILS_MILLS_ID,CITY,ILS_OWNER,MILL_ID,MILL_NAME,PRIMARY_MILL_TYPE,STATE_PROVINCE,TL_AREA,TL_REGION",PL_MI.PORTFOLIO_PL_MI_FACT_TOTAL_PINE_ROUNDWOOD_DEMAND,"CK,CHIP_PRODUCTION_RATE,CHIP_PRODUCTION,FORISK_MILL_ID,ILS_MILL_ID,MILL_CAPACITY_ID,MILL_STATUS_ID_MI,MILL_STATUS_ID_FORISK,MILL_TYPE,PELLET_ADJUSTMENT,PINE_ROUNDWOOD_DEMAND,PINE_ROUNDWOOD_DEMAND_ADJUSTMENT,SPECIES_MULTIPLIER,OPERATING_RATE,WOOD_DEMAND_AT_CAPACITY,WOOD_DEMAND_AT_CAPACITY_ADJUSTED"
    ATTR_ACCUM_MODE = Only Use Result
    COMBINE_GEOM = Use Result
    DATASET = DEV_snowflake_QA-CDO-PORTFOLIO-MANAGEMENT-PL-MI_srvacct
    FEATURETYPES = PL_MI.DIM_MI_MILL PL_MI.PORTFOLIO_PL_MI_FACT_TOTAL_PINE_ROUNDWOOD_DEMAND
    FORMAT = SNOWFLAKE_NONSPATIAL
    GEOMETRY_TYPES = PL_MI.DIM_MI_MILL,""",fme_area,fme_collection,fme_line,fme_point""",PL_MI.PORTFOLIO_PL_MI_FACT_TOTAL_PINE_ROUNDWOOD_DEMAND,""",fme_area,fme_collection,fme_line,fme_point"""
    ORDER_RESULTS = No
    OUTPUT_ADD_SCHEMA_ATTRIBUTES = NO
    OUTPUT_FEATURES_DISPLAY = Schema and Data Features
    SNOWFLAKE_NONSPATIAL_COERCE_VARIANT_TO_JSON = No
    SNOWFLAKE_NONSPATIAL_CREATE_FEATURE_TABLES_FROM_DATA = Yes
    SNOWFLAKE_NONSPATIAL_NAMED_CONNECTION = DEV_snowflake_QA-CDO-PORTFOLIO-MANAGEMENT-PL-MI_srvacct
    SNOWFLAKE_NONSPATIAL_QUERY_FEATURE_TYPES_FOR_MERGE_FILTERS = Yes
    SNOWFLAKE_NONSPATIAL_QUERY_TIMEOUT = 30
    PL_MI.PORTFOLIO_PL_MI_FACT_TOTAL_PINE_ROUNDWOOD_DEMAND -> FeatureMerger [REQUESTOR]
    PL_MI.DIM_MI_MILL -> FeatureMerger [SUPPLIER]
Note: Warning: Rejects null and missing keys
FeatureMerger
    ATTR_ACCUM_MODE = Merge Supplier
    ATTR_CONFLICT_RES = Use Requestor
    IGNORE_NULLS = No
    JOIN_KEYS = @Value(ILS_MILL_ID) @Value(ILS_MILLS_ID) AUTO
    MERGE_TYPE = Attributes Only
    PROCESS_DUPS = NO
    REJECT_NULL_MISSING_KEYS = No
    SUPPLIERS_FIRST = No
    MERGED -> FeatureJoiner_2 [RIGHT]
Mills (reader GEODATABASE_SDE_1)
    attributes: OBJECTID integer, Source char(255), MillID integer, MillName char(255), ParentCompany char(255), City char(255), State char(255), PrimaryMillType char(255), SubMillType char(255), Status char(255), TL_Region char(100), TL_Area char(100), MicroMarketName char(50), MicroMarketID smallint, Latitude double, Longitude double, ModifiedOn date, Address1 char(255), Address2 char(255), Address3 char(255), Country char(50), ZipCode char(10), DestinationID char(50), LIMSName char(100), MapLabel char(255), ForiskID char(50), ForiskName char(200), ForiskStatus char(50), Region char(50), Capacity double,
      Units char(50), Species char(50), EndUse char(200), Demand_tons integer, RecycledPct double, Newsprint double, Printing_Writing double, Household_Sanitary double, Packaging double, Specialty_DissolvingPulp double, MarketPulp double, Certification char(50)
    -> FeatureJoiner_2 [LEFT]
FeatureJoiner_2
    ATTR_CONFLICT_RES = Prefer Left
    GEOMETRY_HANDLING = Prefer Left
    JOIN_KEYS = MillID MILL_ID AUTO
    JOIN_MODE = Inner
    JOINED -> AttributeManager
AttributeManager
    ATTR_TABLE:
      RENAME_SET_VALUE CITY > CITY2 (varchar(16777216))
      RENAME_SET_VALUE TL_AREA > TL_AREA2 (varchar(16777216))
      RENAME_SET_VALUE TL_REGION > TL_REGION2 (varchar(16777216))
    USER_EXPOSED_ATTRIBUTES = ILS_MILLS_ID,CITY,ILS_OWNER,MILL_ID,MILL_NAME,PRIMARY_MILL_TYPE,STATE_PROVINCE,TL_AREA,TL_REGION,CK,CHIP_PRODUCTION_RATE,CHIP_PRODUCTION,FORISK_MILL_ID,ILS_MILL_ID,MILL_CAPACITY_ID,MILL_STATUS_ID_MI,MILL_STATUS_ID_FORISK,MILL_TYPE,PELLET_ADJUSTMENT,PINE_ROUNDWOOD_DEMAND,PINE_ROUNDWOOD_DEMAND_ADJUSTMENT,SPECIES_MULTIPLIER,OPERATING_RATE,WOOD_DEMAND_AT_CAPACITY,WOOD_DEMAND_AT_CAPACITY_ADJUSTED,OBJECTID,Source,MillID,MillName,ParentCompany,City,State,PrimaryMillType,SubMillType,Status,TL_Region,TL_Area,MicroMarketName,MicroMarketID,Latitude,Longitude,ModifiedOn,Address1,Address2,Address3,Country,ZipCode,DestinationID,LIMSName,MapLabel,ForiskID,ForiskName,ForiskStatus,Region,Capacity,Units,Species,EndUse,Demand_tons,RecycledPct,Newsprint,Printing_Writing,Household_Sanitary,Packaging,Specialty_DissolvingPulp,MarketPulp,Certification
    -> SDE_FIRST_FeatureWriter [Output]
    -> Portal_TPRWD [Inserted]
SDE_FIRST_FeatureWriter: FeatureWriter
    DATASET = TLDEVDBSFRS01_FIRST_FIRSTDW_Editor_V2
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = TLDEVDBSFRS01_FIRST_FIRSTDW_Editor_V2
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
    SUMMARY -> Did_Write_Succeed
Did_Write_Succeed: Tester
    BOOL_OP = OR
    TEST_CLAUSE = TEST @Value(_total_features_written) > 0
    TEST_MODE = TEST
    FAILED -> Exit_Code_Check
Exit_Code_Check: Terminator
    MESSAGE = TPRWD write failed.
Portal_TPRWD: FeatureWriter
    ARCGISPORTALFEATURES_ASYNC_WRITE = NO
    ARCGISPORTALFEATURES_AUTH_TYPE = generate_token
    ARCGISPORTALFEATURES_DESTINATION_DATASETTYPE_VALIDATION = Yes
    ARCGISPORTALFEATURES_EXISTING_FEATURE_SERVICE_HANDLING = DROP_CREATE
    ARCGISPORTALFEATURES_FEATURESERVICE_NAME = ILS_TPRWD
    ARCGISPORTALFEATURES_FEATURES_PER_REQUEST = 1000
    ARCGISPORTALFEATURES_FEATURE_SERVICE_CREATE_FILEGDB = YES
    ARCGISPORTALFEATURES_FEATURE_SERVICE_HANDLING = CREATE_IF_MISSING
    ARCGISPORTALFEATURES_FEATURE_SERVICE_SELECTION_SOURCE = User
    ARCGISPORTALFEATURES_FOLDER_NAME = FIRST_TPRWD
    ARCGISPORTALFEATURES_PASSWORD =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
    ARCGISPORTALFEATURES_TARGET_WKID = 102100
    ARCGISPORTALFEATURES_USER = svc-fme
    ARCGISPORTALFEATURES_USE_BRANCH_VERSIONING = NO
    ARCGISPORTALFEATURES_USE_GLOBAL_ID = No
    ARCGISPORTALFEATURES_VERIFY_HTTPS = Yes
    DATASET = https://webgis-uat.weyer.com/gisportal
    DATASET_ATTR = _dataset
    FEATURE_TYPE_LIST_ATTR = _feature_types
    FORMAT = ARCGISPORTALFEATURES
    TOTAL_FEATURES_WRITTEN_ATTR = _total_features_written
    SUMMARY -> Did_Write_Succeed_2
Did_Write_Succeed_2: Tester
    BOOL_OP = OR
    TEST_CLAUSE = TEST @Value(_total_features_written) > 0
    TEST_MODE = TEST
    FAILED -> Exit_Code_Check_2
Exit_Code_Check_2: Terminator
    MESSAGE = ILS TPRWD portal write failed.
