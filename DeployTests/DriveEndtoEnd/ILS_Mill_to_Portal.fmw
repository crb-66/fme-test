FME workspace ILS_Mill_to_Portal.fmw

Parameters:
- DestDataset_ARCGISPORTALFEATURES = https://webgis-uat.weyer.com/gisportal   # Portal URL
- SourceDataset_MSSQL_SPATIAL = ILS   # Database

Readers:
- MSSQL_SPATIAL_1: MSSQL_SPATIAL from $(SourceDataset_MSSQL_SPATIAL)

Writers:
- ARCGISPORTALFEATURES_1: ARCGISPORTALFEATURES to $(DestDataset_ARCGISPORTALFEATURES) in USA_Contiguous_Albers_Equal_Area_Conic

Mills (reader MSSQL_SPATIAL_1)
    attributes: OBJECTID integer, Source varchar(255), MillID integer, MillName varchar(255), ParentCompany varchar(255), City varchar(255), State varchar(255), PrimaryMillType varchar(255), SubMillType varchar(255), Status varchar(255), TL_Region varchar(100), TL_Area varchar(100), MicroMarketName varchar(50), MicroMarketID smallint, Latitude numeric(38,8), Longitude numeric(38,8), ModifiedOn datetime2, Address1 varchar(255), Address2 varchar(255), Address3 varchar(255), Country varchar(50), ZipCode varchar(10), DestinationID varchar(50), LIMSName varchar(100), MapLabel varchar(255), ForiskID varchar(50), ForiskName varchar(200), ForiskStatus varchar(50), Region varchar(50), Capacity numeric(38,4),
      Units varchar(50), Species varchar(50), EndUse varchar(200), Demand_tons integer, RecycledPct numeric(38,4), Newsprint numeric(38,4), Printing_Writing numeric(38,4), Household_Sanitary numeric(38,4), Packaging numeric(38,4), Specialty_DissolvingPulp numeric(38,4), MarketPulp numeric(38,4), Certification varchar(50)
    -> OneMill_from_FME (writer ARCGISPORTALFEATURES_1)
OneMill_from_FME (writer ARCGISPORTALFEATURES_1)
    attributes: OBJECTID Integer, Source String(255), MillID Integer, MillName String(255), ParentCompany String(255), City String(255), State String(255), PrimaryMillType String(255), SubMillType String(255), Status String(255), TL_Region String(100), TL_Area String(100), MicroMarketName String(50), MicroMarketID SmallInteger, Latitude Double, Longitude Double, ModifiedOn Date, Address1 String(255), Address2 String(255), Address3 String(255), Country String(50), ZipCode String(10), DestinationID String(50), LIMSName String(100), MapLabel String(255), ForiskID String(50), ForiskName String(200), ForiskStatus String(50), Region String(50), Capacity Single,
      Units String(50), Species String(50), EndUse String(200), Demand_tons Integer, RecycledPct Single, Newsprint Single, Printing_Writing Single, Household_Sanitary Single, Packaging Single, Specialty_DissolvingPulp Single, MarketPulp Single, Certification String(50)
