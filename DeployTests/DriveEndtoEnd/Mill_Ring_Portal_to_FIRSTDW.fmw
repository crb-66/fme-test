FME workspace Mill_Ring_Portal_to_FIRSTDW.fmw

Parameters:
- DestDataset_GEODATABASE_SDE = D:\FME_Share\TLDEVDBSFRS01_FIRST_FIRSTDW_Editor.sde   # Connection File
- SourceDataset_ARCGISPORTALFEATURES = https://webgis-uat.weyer.com/gisportal   # Portal URL

Readers:
- ARCGISPORTALFEATURES_1: ARCGISPORTALFEATURES from $(SourceDataset_ARCGISPORTALFEATURES)

Writers:
- GEODATABASE_SDE_1: GEODATABASE_SDE to $(DestDataset_GEODATABASE_SDE)

FIRST_RINGS (reader ARCGISPORTALFEATURES_1)
    attributes: objectid OID(4), name String(40), frombreak Double, tobreak Double, facilityoid Integer, facilityid Integer, name_1 String(20), source String(6), millid Integer, millname String(48), parentcompany String(26), city String(12), state String(4), primarymilltype String(20), submilltype String(30), tl_region String(8), tl_area String(12), micromarketname String(22), micromarketid Integer, latitude Double, longitude Double, modifiedon Date, address1 String(20), address2 String(8), address3 String(8), country String(4), zipcode String(10), destinationid String(12), limsname String(36), maplabel String(48),
      foriskid String(14), foriskname String(22), foriskstatus String(8), region String(20), capacity Double, units String(8), species String(18), enduse String(12), demand_tons Integer, recycledpct Double, newsprint Double, printing_writing Double, household_sanitary Double, packaging Double, specialty_dissolvingpulp Double, marketpulp Double, certification String(255), breaks String(8), additionaltime Double, additionaldistance Double, SHAPE__Length Double, SHAPE__Area Double
    -> MillsRingTest (writer GEODATABASE_SDE_1)
MillsRingTest (writer GEODATABASE_SDE_1)
    attributes: objectid integer, name char(40), frombreak double, tobreak double, facilityoid integer, facilityid integer, name_1 char(20), source char(6), millid integer, millname char(48), parentcompany char(26), city char(12), state char(4), primarymilltype char(20), submilltype char(30), tl_region char(8), tl_area char(12), micromarketname char(22), micromarketid integer, latitude double, longitude double, modifiedon date, address1 char(20), address2 char(8), address3 char(8), country char(4), zipcode char(10), destinationid char(12), limsname char(36), maplabel char(48),
      foriskid char(14), foriskname char(22), foriskstatus char(8), region char(20), capacity double, units char(8), species char(18), enduse char(12), demand_tons integer, recycledpct double, newsprint double, printing_writing double, household_sanitary double, packaging double, specialty_dissolvingpulp double, marketpulp double, certification char(255), breaks char(8), additionaltime double, additionaldistance double, SHAPE__Length double, SHAPE__Area double
