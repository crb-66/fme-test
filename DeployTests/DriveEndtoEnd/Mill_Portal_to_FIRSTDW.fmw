FME workspace Mill_Portal_to_FIRSTDW.fmw

Parameters:
- DestDataset_GEODATABASE_SDE = D:\FME_Share\TLDEVDBSFRS01_FIRST_FIRSTDW_Editor.sde   # Connection File
- SourceDataset_ARCGISPORTALFEATURES_3 = https://webgis-uat.weyer.com/gisportal   # Portal URL

Readers:
- ARCGISPORTALFEATURES_2: ARCGISPORTALFEATURES from $(SourceDataset_ARCGISPORTALFEATURES_3)

Writers:
- GEODATABASE_SDE_1: GEODATABASE_SDE to $(DestDataset_GEODATABASE_SDE)

FIRST_MILLS (reader ARCGISPORTALFEATURES_2)
    attributes: objectid OID(4), country String(4), specialty_dissolvingpulp Double, source String(6), millname String(48), parentcompany String(26), state String(4), limsname String(36), additionaldistance Double, longitude Double, marketpulp Double, tl_region String(8), foriskid String(14), micromarketid Integer, certification String(255), zipcode String(10), modifiedon Date, tobreak Double, demand_tons Integer, name String(38), analysisarea Double, region String(20), name_1 String(20), primarymilltype String(20), maplabel String(48), city String(12), latitude Double, units String(8), millid Integer, capacity Double,
      household_sanitary Double, submilltype String(30), recycledpct Double, enduse String(12), newsprint Double, foriskname String(22), address3 String(8), breaks String(8), address2 String(8), address1 String(20), facilityoid Integer, packaging Double, destinationid String(12), frombreak Double, foriskstatus String(8), tl_area String(12), micromarketname String(22), additionaltime Double, species String(18), printing_writing Double, SHAPE__Length Double, SHAPE__Area Double
    -> MillsDriveTest (writer GEODATABASE_SDE_1)
MillsDriveTest (writer GEODATABASE_SDE_1)
    attributes: objectid integer, country char(4), specialty_dissolvingpulp double, source char(6), millname char(48), parentcompany char(26), state char(4), limsname char(36), additionaldistance double, longitude double, marketpulp double, tl_region char(8), foriskid char(14), micromarketid integer, certification char(255), zipcode char(10), modifiedon date, tobreak double, demand_tons integer, name char(38), analysisarea double, region char(20), name_1 char(20), primarymilltype char(20), maplabel char(48), city char(12), latitude double, units char(8), millid integer, capacity double,
      household_sanitary double, submilltype char(30), recycledpct double, enduse char(12), newsprint double, foriskname char(22), address3 char(8), breaks char(8), address2 char(8), address1 char(20), facilityoid integer, packaging double, destinationid char(12), frombreak double, foriskstatus char(8), tl_area char(12), micromarketname char(22), additionaltime double, species char(18), printing_writing double, SHAPE__Length double, SHAPE__Area double
