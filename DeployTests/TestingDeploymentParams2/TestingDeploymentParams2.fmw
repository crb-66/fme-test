FME workspace TestingDeploymentParams2.fmw

Parameters:
- SourceDataset_GEODATABASE_SDE = $(FME_DEV_ETL_FIRSTStaging_Viewer)   # ArcSDE Geodatabase Connection
- DestDataset_GEODATABASE_SDE = $(FME_DEV_ETL_FIRSTStaging_Editor)   # ArcSDE Geodatabase Connection

Readers:
- GEODATABASE_SDE_1: GEODATABASE_SDE from $(SourceDataset_GEODATABASE_SDE)

Writers:
- GEODATABASE_SDE_2: GEODATABASE_SDE to $(DestDataset_GEODATABASE_SDE)

State (reader GEODATABASE_SDE_1)
    attributes: OBJECTID integer, StateName char(50), StateAbbr char(2), StateFip char(2), Shape.STArea() double, Shape.STLength() double
    -> WriteTest (writer GEODATABASE_SDE_2)
WriteTest (writer GEODATABASE_SDE_2)
    attributes: OBJECTID integer, StateName char(50), StateAbbr char(2), StateFip char(2), Shape_STArea__ double, Shape_STLength__ double
